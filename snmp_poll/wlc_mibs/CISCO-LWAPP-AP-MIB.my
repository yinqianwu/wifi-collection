-- *******************************************************************
-- CISCO-LWAPP-AP-MIB.my 
-- January 2006, Devesh Pujari, Prasanna Viswakumar, Srinath Candadai
-- August 2010, Suja Thangaveluchamy
-- Copyright (c) 2006-2007, 2010-2012, 2016 by Cisco Systems, Inc.
-- All rights reserved.
-- *******************************************************************

CISCO-LWAPP-AP-MIB DEFINITIONS ::= BEGIN

IMPORTS 
        MODULE-IDENTITY, 
        OBJECT-TYPE,
        NOTIFICATION-TYPE,
        Unsigned32,
        Counter32,
        TimeTicks,
        Gauge32,
        Integer32
                FROM SNMPv2-SMI
        MODULE-COMPLIANCE, 
        NOTIFICATION-GROUP,
        OBJECT-GROUP
                FROM SNMPv2-CONF
        DisplayString,
        TruthValue,
        MacAddress,
        TimeInterval,
        RowStatus,
        TimeStamp,
        DateAndTime
                FROM SNMPv2-TC 
        SnmpAdminString
                FROM SNMP-FRAMEWORK-MIB 
        PhysicalIndex
                FROM ENTITY-MIB
        InetAddressType,
        InetAddress,
        InetPortNumber
                FROM INET-ADDRESS-MIB
        CLApIfType,
        CLDot11Channel,
        CLApAssocFailureReason,
        CLApDot11RadioSubband,
        CLApDot11RadioRole,
        CLApMode
                FROM CISCO-LWAPP-TC-MIB
        cldRegulatoryDomain
                FROM CISCO-LWAPP-DOT11-MIB
        cLWlanIndex
                FROM CISCO-LWAPP-WLAN-MIB
        ciscoMgmt
                FROM CISCO-SMI
        Unsigned64
                FROM CISCO-TC
        cLRFProfileHighDensityMaxRadioClients,
        cLRFProfileHDClientTrapThreshold
                FROM CISCO-LWAPP-RF-MIB
        IANAifType
                FROM IANAifType-MIB;

--********************************************************************
--*  MODULE IDENTITY
--********************************************************************
ciscoLwappApMIB        MODULE-IDENTITY
    LAST-UPDATED    "201206130000Z"
        ORGANIZATION   "Cisco Systems Inc."
        CONTACT-INFO  
               "        Cisco Systems,
                        Customer Service

                Postal: 170 West Tasman Drive
                        San Jose, CA  95134
                        USA

                   Tel: +1 800 553-NETS

                 Email: cs-snmp@cisco.com"

        DESCRIPTION             
                "This MIB is intended to be implemented on all those
                devices operating as Central Controllers (CC) that
                terminate the Light Weight Access Point Protocol
                tunnel from Light-weight LWAPP Access Points.

                This MIB provides configuration and status information
                about the 802.11 Access Points that have joined the
                controller.                 

                The relationship between CC and the LWAPP APs
                can be depicted as follows:

        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  AP  + +  AP  +     +  AP  +      +  AP  +          +  AP  +
   +      + +      +     +      +      +      +          +      +
   +......+ +......+     +......+      +......+          +......+
              .              .             .                 .
            .  .              .             .                 .
           .    .              .             .                 .
          .      .              .             .                 .
         .        .              .             .                 .
      +......+ +......+     +......+      +......+          +......+
      +      + +      +     +      +      +      +          +      +
      +  MN  + +  MN  +     +  MN  +      +  MN  +          +  MN  +
      +      + +      +     +      +      +      +          +      +
      +......+ +......+     +......+      +......+          +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.
               
                                   GLOSSARY
 
                Access Point ( AP )

                An entity that contains an 802.11 medium access
                control ( MAC ) and physical layer ( PHY ) interface
                and provides access to the distribution services via
                the wireless medium for associated clients.  

                LWAPP APs encapsulate all the 802.11 frames in
                LWAPP frames and sends it to the controller to which
                it is logically connected.


		Bluetooth Low Energy  (BLE)
	
		Bluetooth Low Energy is a light-weight subset of classic
		bluetooth which is added in Hyper Action Location (HALO) 
		enabled APs to make use of BLE beacons to communicate 
		with wireless clients at short range.
				

                Basic Service Set Identifier (BSSID)

                The identifier for the service set comprising of
                all the 802.11 stations under the control of
                one coordinating Access Point.  This identifier
                happens to be the MAC address of the dot11 radio
                interface of the Access Point.  The wireless
                clients that associate with the Access Point
                get the wired uplink through this particular 
                dot11 interface. 

                Central Controller ( CC )

                The central entity that terminates the LWAPP protocol
                tunnel from the LWAPP APs.  Throughout this MIB,
                this entity also referred to as 'controller'. 

		Hyper Action Location (HALO)

	 	This is an external module for Cisco Access Points,
		which is responsible for high accuracy indoor 
		location. It includes smart antenna and new software
		interfaces to enable high accuracy indoor location.	

		iBeacon

		This is a low-cost transmitter which can transmit 
		its own unique identification number to the local 
		area.	

                Light Weight Access Point Protocol ( LWAPP ) 

                This is a generic protocol that defines the 
                communication between the Access Points and the
                Central Controller. 

                Mobile Node ( MN )

                A roaming 802.11 wireless device in a wireless
                network associated with an access point. 

                Station Management (SMT)

                This term refers to the internal management of the
                802.11 protocol operations by the AP to work
                cooperatively with the other APs and 802.11
                devices in the network.
                
                Link Latency 
                
                Latency is round trip time between AP and controller.
                There is a continuous heart-beat between AP and 
                controller. AP calculates latency for each time and 
                sends to controller.
		
		AMSDU
		
		Aggregate MAC Service Data Unit. A structure containing 
		multiple MSDUs, transported within a single (unfragmented)  
		or multiple (fragmented) Data MPDU. 

        DTLS

        Datagram Transport Layer Security (DTLS) protocol provides 
        communications privacy for datagram protocols. The protocol 
        allows client/server applications to communicate in a way 
        that is designed to prevent eavesdropping, tampering, or 
        message forgery. 

        WIPS

        Wireless Intrusion Prevention System (WIPS) is a network device 
        that monitors the radio spectrum for the presence of 
        unauthorized access points (intrusion detection), and can 
        automatically take countermeasures (intrusion prevention).

        SE

        Spectrum Expert is an application software, which when 
        connected to Spectrum Intelligent Access Point, provides 
        detailed RF spectrum plots and data, and assist in diagnosing 
        network problems. 

	PPPOE

	Point-to-Point Protocol Over Ethernet provides a standard method 
	to build sessions for transporting multi-protocol datagrams between 
	point-to-point links over Ethernet.

                REFERENCE
 
                [1] Part 11 Wireless LAN Medium Access Control ( MAC )
                and Physical Layer ( PHY ) Specifications.
  
                [2] Draft-obara-capwap-lwapp-00.txt, IETF Light 
                Weight Access Point Protocol. "
    REVISION        "201206130000Z"
    DESCRIPTION
        "Added ciscoLwappDot11IfAntennaGroup and
        ciscoLwappRetransmitGroup"
    REVISION        "201102070000Z"
    DESCRIPTION
        "Addressed Approver's comments."
    REVISION        "201101210000Z"
    DESCRIPTION
        "Addressed reviwer's comments."
    REVISION        "201101100000Z"
    DESCRIPTION
        "Addressed reviewer's comments."
    REVISION        "201012130000Z"
    DESCRIPTION
        "Addressed Reviwer's comments"
    REVISION        "201008190000Z"
    DESCRIPTION
        "Added cLApGlobal, cLApCredentials, cLSpectrum,
        cLAp802dot1xSupplicant mib objects.
        Added link latency tables, cLApEncryptionEnable.
        cLApDot11RadioTable have been added to provide support
        for subband radios.
        AP uptime, join time, join taken time and Ethernet slot info
        have been added to clApTable.  cLApEthernetIfTable which
        provides Ethernet interface status and statistics information
        has been added.
        The group ciscoLwappApGroupSup3, ciscoLwappApGroupSup4,
        ciscoLwappApNotifObjsGroup and ciscoLwappApNotifsGroup 
        have been added."
    REVISION        "200701030000Z"
    DESCRIPTION
        "The object cLApName has been added."
        REVISION      "200607180000Z"
        DESCRIPTION
                "Added cLApEntPhysicalIndex object."
        REVISION      "200603300000Z"
        DESCRIPTION
                "Initial version of this MIB module. "
        ::= { ciscoMgmt 513 }

ciscoLwappApMIBNotifs  OBJECT IDENTIFIER      ::= { ciscoLwappApMIB 0 }
ciscoLwappApMIBObjects OBJECT IDENTIFIER      ::= { ciscoLwappApMIB 1 }
ciscoLwappApMIBConform OBJECT IDENTIFIER      ::= { ciscoLwappApMIB 2 }
ciscoLwappApMIBNotifObjects OBJECT IDENTIFIER ::= { ciscoLwappApMIB 3 }

ciscoLwappAp   OBJECT IDENTIFIER ::= { ciscoLwappApMIBObjects 1 }
ciscoLwappApIf OBJECT IDENTIFIER ::= { ciscoLwappApMIBObjects 2 }
ciscoLwappApGlobal   OBJECT IDENTIFIER ::= { ciscoLwappApMIBObjects 3 }
ciscoLwappApCredentials OBJECT IDENTIFIER ::= { ciscoLwappApMIBObjects 4 } 
ciscoLwappLinkLatency   OBJECT IDENTIFIER ::= { ciscoLwappApMIBObjects 5 }
ciscoLwappSpectrum   OBJECT IDENTIFIER ::= { ciscoLwappApMIBObjects 6 }
ciscoLwappAp802dot1xSupplicant   OBJECT IDENTIFIER ::= { ciscoLwappApMIBObjects 7 }
ciscoLwappApWlanStats   OBJECT IDENTIFIER ::= { ciscoLwappApMIBObjects 9 }

ciscoLwappApWlanInfo   OBJECT IDENTIFIER ::= { ciscoLwappApMIBObjects 10 }
ciscoLwappPacketDumpInfo   OBJECT IDENTIFIER ::= { ciscoLwappApMIBObjects 11 }

ciscoLwappAplanStats    OBJECT IDENTIFIER ::= { ciscoLwappApMIBObjects 12 }

ciscoLwappApGlobalBleBeacon  OBJECT IDENTIFIER ::= { ciscoLwappApMIBObjects 13 }

-- ********************************************************************
-- APs that have joined the controller
-- ********************************************************************

cLApTable OBJECT-TYPE
        SYNTAX     SEQUENCE OF CLApEntry
        MAX-ACCESS not-accessible
        STATUS     current
        DESCRIPTION
                "This table represents the information about the
                802.11 LWAPP Access Points that have joined the
                controller.

                LWAPP APs exchange configuration messages with the
                controller and get the required configuration for
                their 802.11 related operations, after they join the
                controller. "
        ::= { ciscoLwappAp 1 }

cLApEntry OBJECT-TYPE
        SYNTAX     CLApEntry
        MAX-ACCESS not-accessible
        STATUS     current
        DESCRIPTION
                "Each entry in this table provides information about
                one 802.11 LWAPP Access Point that has joined the
                controller.

                Entries are removed when the APs lose their
                association with the controller due to loss
                of communication. "
        INDEX   { cLApSysMacAddress }
        ::= { cLApTable 1 }

CLApEntry ::= SEQUENCE {
                cLApSysMacAddress                  MacAddress,  
                cLApIfMacAddress                   MacAddress,
                cLApMaxNumberOfDot11Slots          Unsigned32,
                cLApEntPhysicalIndex               PhysicalIndex, 
                cLApName                           SnmpAdminString,
                cLApUpTime                         TimeTicks,
                cLLwappUpTime                      TimeTicks,
                cLLwappJoinTakenTime               TimeTicks,
                cLApMaxNumberOfEthernetSlots       Unsigned32,
                cLApPrimaryControllerAddressType   InetAddressType,
                cLApPrimaryControllerAddress       InetAddress,
                cLApSecondaryControllerAddressType InetAddressType,
                cLApSecondaryControllerAddress     InetAddress,
                cLApTertiaryControllerAddressType  InetAddressType,
                cLApTertiaryControllerAddress      InetAddress,
                cLApLastRebootReason               INTEGER,
                cLApEncryptionEnable               TruthValue,
                cLApFailoverPriority		   INTEGER,
                cLApPowerStatus		           INTEGER,
                cLApTelnetEnable                   TruthValue,
                cLApSshEnable                      TruthValue,
                cLApPreStdStateEnabled             TruthValue,
                cLApPwrInjectorStateEnabled        TruthValue,
                cLApPwrInjectorSelection           INTEGER,
                cLApPwrInjectorSwMacAddr           MacAddress,
                cLApWipsEnable                     TruthValue,
                cLApMonitorModeOptimization        INTEGER,
                cLApDomainName                     SnmpAdminString,
                cLApNameServerAddressType          InetAddressType,
                cLApNameServerAddress              InetAddress,
                cLApAMSDUEnable			           TruthValue,
                cLApEncryptionSupported            TruthValue,
                cLApRogueDetectionEnabled          TruthValue,
		        cLApTcpMss			            INTEGER,
		        cLApDataEncryptionStatus	    TruthValue,
                cLApNsiKey                         DisplayString,
		        cLApAdminStatus			   TruthValue,
                cLApPortNumber                     InetPortNumber,
                cLApRetransmitCount                Unsigned32,
                cLApRetransmitTimeout              Unsigned32,
                cLApVenueConfigVenueGroup          INTEGER,
                cLApVenueConfigVenueType           INTEGER,
                cLApVenueConfigVenueName           SnmpAdminString,
                cLApVenueConfigLanguage            SnmpAdminString,
                cLApLEDState                       TruthValue,
                cLApTrunkVlan			           Unsigned32,
                cLApTrunkVlanStatus		           TruthValue,
                cLApLocation                       SnmpAdminString,
                cLApSubMode	                       INTEGER,
                cLApAssocCount                     Unsigned32,
                cLApAssocFailResourceCount         Unsigned32,
                cLApRealTimeStatsModeEnabled       TruthValue,
                cLApAssociatedClientCount          Unsigned32,
                cLApMemoryCurrentUsage             Unsigned32,
                cLApMemoryAverageUsage             Unsigned32,
                cLApCpuCurrentUsage                Unsigned32,
                cLApCpuAverageUsage                Unsigned32, 				
                cLApUpgradeFromVersion             DisplayString,
                cLApUpgradeToVersion               DisplayString,
                cLApUpgradeFailureCause            DisplayString,
                cLApMaxClientLimitNumberTrap       Unsigned32,
                cLApMaxClientLimitCause            DisplayString,
                cLApMaxClientLimitSet              TruthValue,
                cLApFloorLabel                     Unsigned64,
                cLApConnectCount                   Unsigned32,	
                cLApReassocSuccCount               Counter32,
                cLApReassocFailCount               Counter32,
                cLAdjChannelRogueEnabled           TruthValue,				
                cLApAssocFailCountByRate           Unsigned32,
                cLApAbnormalOfflineCount           Unsigned32,
                cLApActiveClientCount              Unsigned32, 
                cLApAssocFailCountForRssiLow       Unsigned32,
                cLApSysNetId                       SnmpAdminString,
		cLApAssocFailTimes                 Counter32,
		cLApAntennaBandMode	           INTEGER,
		cLApHeartBeatRspAvgTime            INTEGER,
		cLApEchoRequestCount               Counter32,
		cLApEchoResponseLossCount          Counter32,
		cLApModuleInserted                 DisplayString, 
		cLApEnableModule                   TruthValue,
		cLApIsUniversal                    TruthValue,
		cLApUniversalPrimeStatus           DisplayString,
                cLApIsMaster                       TruthValue,
		cLApBleFWDownloadStatus            TruthValue,
                cLApDot11XorDartConnectorStatus    DisplayString
		}

	cLApSysMacAddress OBJECT-TYPE
		SYNTAX     MacAddress
		MAX-ACCESS not-accessible
		STATUS     current
		DESCRIPTION
			"This object represents the radio MAC address 
			common to the dot11 interfaces of the AP
			and uniquely identifies an entry in this table. "
		::= { cLApEntry 1 }

	cLApIfMacAddress OBJECT-TYPE
		SYNTAX     MacAddress
		MAX-ACCESS read-only
		STATUS     current
		DESCRIPTION
			"This object represents the Ethernet MAC address of
			the AP. " 
		::= { cLApEntry 2 }

	cLApMaxNumberOfDot11Slots OBJECT-TYPE
		SYNTAX     Unsigned32
		MAX-ACCESS read-only
		STATUS     current
		DESCRIPTION
			"This object represents the maximum number of
			802.11 radio interface slots in this AP. "
		::= { cLApEntry 3 }

	cLApEntPhysicalIndex OBJECT-TYPE
		SYNTAX     PhysicalIndex 
		MAX-ACCESS read-only
		STATUS     current
		DESCRIPTION
			"This object provides the index value in the 
			entPhysicalEntry corresponding to this AP." 
		::= { cLApEntry 4 }

	cLApName OBJECT-TYPE
		SYNTAX SnmpAdminString (SIZE(0..32))
		MAX-ACCESS read-write
		STATUS current
		DESCRIPTION
			"This object represents the administrative name 
		assigned to the AP by the user. If an AP is not configured, 
		its factory default name will be ap:<last three byte 
		of MACAddress> eg. ap:af:12:be." 
		::= {  cLApEntry 5 }

	cLApUpTime OBJECT-TYPE
		SYNTAX TimeTicks
		MAX-ACCESS read-only
		STATUS current
		DESCRIPTION
		"This object represents the time in hundredths
		of a second since the last time the AP rebooted." 
		::= {  cLApEntry 6 }

	cLLwappUpTime OBJECT-TYPE
		SYNTAX TimeTicks
		MAX-ACCESS read-only
		STATUS current
		DESCRIPTION
		"This object represents the time in hundredths
		of a second since the last time the AP joined 
		the controller." 
		::= {  cLApEntry 7 }

	cLLwappJoinTakenTime OBJECT-TYPE
		SYNTAX TimeTicks
		MAX-ACCESS read-only
		STATUS current
		DESCRIPTION
		"This object represents the time taken in hundredths
		of a second for the AP to join the controller. This 
		could be a significant value in Mesh environments." 
		::= {  cLApEntry 8 }

	cLApMaxNumberOfEthernetSlots OBJECT-TYPE
		SYNTAX     Unsigned32
		MAX-ACCESS read-only
		STATUS     current
		DESCRIPTION
			"This object represents the maximum number of
			Ethernet slots in this AP. "
		::= { cLApEntry 9 }

	cLApPrimaryControllerAddressType OBJECT-TYPE
	       SYNTAX      InetAddressType 
	       MAX-ACCESS  read-write
	       STATUS      current
	       DESCRIPTION
		       "This object represents the type of the primary 
		       controller's address made available through 
		       cLApPrimaryControllerAddress."
		::= {  cLApEntry 10 }

	cLApPrimaryControllerAddress OBJECT-TYPE
	       SYNTAX      InetAddress
	       MAX-ACCESS  read-write
	       STATUS      current
	       DESCRIPTION
		       "This object represents the address of the primary 
		       controller that the APs will join." 
		::= {  cLApEntry 11 }

	cLApSecondaryControllerAddressType OBJECT-TYPE
	       SYNTAX      InetAddressType 
	       MAX-ACCESS  read-write
	       STATUS      current
	       DESCRIPTION
		       "This object represents the type of the secondary 
		       controller's address made available through 
		       cLApSecondaryControllerAddress."
		::= {  cLApEntry 12 }

	cLApSecondaryControllerAddress OBJECT-TYPE
	       SYNTAX      InetAddress
	       MAX-ACCESS  read-write
	       STATUS      current
	       DESCRIPTION
		       "This object represents the address of the secondary 
		       controller that the APs will join." 
		::= {  cLApEntry 13 }

	cLApTertiaryControllerAddressType OBJECT-TYPE
	       SYNTAX      InetAddressType 
	       MAX-ACCESS  read-write
	       STATUS      current
	       DESCRIPTION
		       "This object represents the type of the tertiary 
		       controller's address made available through 
		       cLApTertiaryControllerAddress."
		::= {  cLApEntry 14 }

	cLApTertiaryControllerAddress OBJECT-TYPE
	       SYNTAX      InetAddress
	       MAX-ACCESS  read-write
	       STATUS      current
	       DESCRIPTION
		       "This object represents the address of the tertiary 
		       controller that the APs will join." 
		::= {  cLApEntry 15 }

	cLApLastRebootReason         OBJECT-TYPE
		SYNTAX     INTEGER {
				none(0),
				dot11gModeChange(1),
				ipAddressSet(2),
				ipAddressReset(3),
				rebootFromController(4),
				dhcpFallbackFail(5),
				discoveryFail(6),
				noJoinResponse(7),
				denyJoin(8),
				noConfigResponse(9),
				configController(10),
				imageUpgradeSuccess(11),
				imageOpcodeInvalid(12),
				imageCheckSumInvalid(13),
				imageDataTimeout(14),
				configFileInvalid(15),
				imageDownloadError(16),
				rebootFromConsole(17),
				rapOverAir(18),
				powerLow(19),
				crash(20),
				powerHigh(21),
				powerLoss(22),
				powerChange(23),
				componentFailure(24),
				watchdog(25),
				lscEnabled(26),
				lscDisabled(27),
				lscProvTimeout(28),
				lscMaxProvReqRetries(29),
				lscLoadFailure(30),
				lscJoinFailure(31),
				capwapTimerFailure(32),
				staticIpFailover(33),
				vlanTagFailover(34),
				capwapDiscoveryRequest(35),
				capwapDiscoveryResponse(36),
				capwapJoinRequest(37),
				capwapJoinResponse(38),
				capwapConfigurationStatus(39),
				capwapConfigurationStatusResponse(40),
				capwapConfigurationUpdateRequest(41),
				capwapConfigurationUpdateResponse(42),
				capwapWtpEventRequest(43),
				capwapWtpEventResponse(44),
				capwapChangeStateEventRequest(45),
				capwapChangeStateEventResponse(46),
				capwapEchoRequest(47),
				capwapEchoResponse(48),
				capwapImageDataRequest(49),
				capwapImageDataResponse(50),
				capwapResetRequest(51),
				capwapResetResponse(52),
				capwapPrimaryDiscoveryRequest(53),
				capwapPrimaryDiscoveryResponse(54),
				capwapDataTransferRequest(55),
				capwapDataTransferResponse(56),
				capwapClearConfigurationRequest(57),
				capwapClearConfigurationResponse(58),
				capwapMobileConfigurationRequest(59),
				capwapMobileConfigurationResponse(60),
				capwapPathMtuRequest(61),
				capwapPathMtuResponse(62)
			    }
		MAX-ACCESS read-only
		STATUS     current
		DESCRIPTION
		"This object represents the reason for the last
		reboot of the AP.
			 none                 - ap reported a reboot reason code
						unknown to the controller.
			 dot11gModeChange     - 11g mode change
			 ipAddressSet         - set static ip address
			 ipAddressReset       - reset static ip address
			 rebootFromController - ap reboot initiated 
						from controller
			 dhcpFallbackFail     - could not fallback to dhcp
			 discoveryFail        - could not send discovery
			 noJoinResponse       - did not receive join response
			 denyJoin             - deny join attempt at 
						the controller
			 noConfigResponse     - did not get config response
			 configController     - found configured or master 
						controller
			 imageUpgradeSuccess  - image upgraded successfully
			 imageOpcodeInvalid   - invalid image data opcode
			 imageCheckSumInvalid - invalid image md5 checksum
			 imageDataTimeout     - image data message timeout
			 configFileInvalid    - invalid config file
			 imageDownloadError   - image download process error
			 rebootFromConsole    - reboot command from ap console
			 rapOverAir           - root access point is connected 
						over the air
			 brownout             - ap rebooted due to power failure
			 powerLow             - ap rebooted dued to low power
						also called as brownout
			 crash                - crashed due to software failure
			 powerHigh            - rebooted due to power spike
			 powerLoss            - rebooted due to power loss
			 powerChange          - rebooted due to change in 
						power source
			 componentFailure     - rebooted due to component 
						failure
			 watchdog             - rebooted due to watch dog 
						timer reset.
			 lscEnabled  - rebooted as LSC was enabled
			 lscDisabled - rebooted as LSC was disabled
			 lscProvTimeout - rebooted due to LSC provision timeout
			 lscMaxProvReqRetries - rebooted due to maximum retries
					 of LSC provision request
			 lscLoadFailure - rebooted due to LSC load failure
			 lscJoinFailure - rebooted due to LSC join failure.
			 capwapTimerFailure - rebooted due to capwap timer
					    failure
			 staticIpFailover - rebooted due to static IP failover
			 vlanTagFailover - rebooted due to vlan tag failover
			 capwapDiscoveryRequest - link failure while processing
						 capwap discovery request
			 capwapDiscoveryResponse - link failure while processing
						 capwap discovery response
			 capwapJoinRequest     - rebooted due to capwap
						  join request
			 capwapJoinResponse    - rebooted due to capwap
						  join response
			 capwapConfigurationStatus- rebooted due to capwap
						    configuration status request
			 capwapConfigurationStatusResponse - rebooted due to 
					   capwap configuration status response
			 capwapConfigurationUpdateRequest- rebooted due to 
					   capwap configuration update request
			 capwapConfigurationUpdateResponse - rebooted due to 
					   capwap configuration update response
			 capwapWtpEventRequest - rebooted due to capwap WTP
						    event request
			 capwapWtpEventResponse - rebooted due to capwap WTP
						    event response
			 capwapChangeStateEventRequest - rebooted due to capwap
						 change state event request
			 capwapChangeStateEventResponse - rebooted due to capwap
						 change state event response
			 capwapEchoRequest      - rebooted due to capwap 
						  echo request
			 capwapEchoResponse     - rebooted due to capwap
						  echo response
			 capwapImageDataRequest - rebooted due to capwap
						    image data request
			 capwapImageDataResponse - rebooted due to capwap
						    image data response
			 capwapResetRequest - rebooted due to capwap 
						    reset request
			 capwapResetResponse - rebooted due to capwap
						    reset response
			 capwapPrimaryDiscoveryRequest - rebooted due to capwap
						primary discovery request
			 capwapPrimaryDiscoveryResponse - rebooted due to capwap
						primary discovery response
			 capwapDataTransferRequest - rebooted due to capwap
						data transfer request
			 capwapDataTransferResponse - rebooted due to capwap
						data transfer response
			 capwapClearConfigurationRequest-rebooted due to capwap
						clear configuration request
			 capwapClearConfigurationResponse-rebooted due to capwap
						clear configuration response
			 capwapMobileConfigurationRequest-rebooted due to capwap
						mobile configuration request
			 capwapMobileConfigurationResponse-rebooted due to capwap
						mobile configuration response
			 capwapPathMtuRequest   - rebooted due to capwap
						  path MTU request
			 capwapPathMtuResponse  - rebooted due to capwap
						  path MTU response." 
		::= { cLApEntry 16 }


	cLApEncryptionEnable OBJECT-TYPE
		SYNTAX     TruthValue
		MAX-ACCESS read-write
		STATUS     current
		DESCRIPTION
			"This object specifies whether encyrption between 
			controller and AP is enabled or not. Encryption
			can only be enabled if ESM card in controller is 
			pluged in.
			
			A value of 'true' enables encryption between 
			controller and AP.
			
			A value of 'false' disables encryption between 
			controller and AP."
			
		DEFVAL { false }
		::=    { cLApEntry 18 }

	cLApFailoverPriority OBJECT-TYPE
	       SYNTAX      INTEGER {
			      low(1),
			      medium(2),
			      high(3),
			      critical(4)
		}
	       MAX-ACCESS  read-write
	       STATUS      current
	       DESCRIPTION
		"This object represents the AP failover priority
		for an AP. If a higher priority AP wishes to join 
		the controller, it will be given preference over 
		a join request from a lower priority AP. Also if the 
		number of AP joined has reached the limit that the 
			controller can support then the controller can disassociate
		an already joined lower priority AP. This priority will be 
		considered only if the cLApGlobalFailoverPriority is 
		Enabled on the controller."
		DEFVAL {low}
		::= {  cLApEntry 19 }


	cLApPowerStatus OBJECT-TYPE
	       SYNTAX      INTEGER {
			      low(1),
			      fifteendotfour(2),
			      sixteendoteight(3),
			      full(4),
			      external(5),
			      twentyfivedotfive(6),
			      mixedmode(7)
		}
	       MAX-ACCESS  read-only
	       STATUS      current
	       DESCRIPTION
		       "This object represents the power status of the AP 
			    low             - The AP is drawing low power from 
					      Ethernet 
			    fifteendotfour  - The AP is drawing 15.4 watts from 
					      Ethernet
			    sixteendoteight - The AP is drawing 16.8 watts from
					      Ethernet
			    twentyfivedotfive - The AP is drawing 25.5 watts from
					      Ethernet
			    full            - The power is high enough for 
					      normal operation of the AP. 
					      The power source could be 
					      Ethernet or external
			    external        - The power source is not from
					      Ethernet.
		mixedmode       - The power is high enough for 
				  operation of AP. In this state 
				  one radio will operate in full 
				  power mode while the other radio 
				  will be powered off or operate 
				  at reduced capacity." 
	       ::= {  cLApEntry 20 }

	cLApTelnetEnable OBJECT-TYPE
		SYNTAX     TruthValue
		MAX-ACCESS read-write
		STATUS     current
		DESCRIPTION
			"This object specifies whether Telnet session
			can be established to the AP. 

			A value of 'true' indicates an Telnet session
			can be established to the AP. 

			A value of 'false' indicates an Telnet session
			cannot be established to the AP."
		DEFVAL { false }
		::=    { cLApEntry 21 }

	cLApSshEnable OBJECT-TYPE
		SYNTAX     TruthValue
		MAX-ACCESS read-write
		STATUS     current
		DESCRIPTION
			"This object specifies whether SSH session
			can be established to the AP. 

			A value of 'true' indicates an SSH session
			can be established to the AP. 

			A value of 'false' indicates an SSH session
			cannot be established to the AP."
		DEFVAL { false }
		::=    { cLApEntry 22 }

	cLApPreStdStateEnabled OBJECT-TYPE
	       SYNTAX      TruthValue
	       MAX-ACCESS  read-write
	       STATUS      current
	       DESCRIPTION
		       "This object represents whether the Pre-Standard state
			of the AP is enabled or disabled.

			A value of 'true' denotes that the Pre-Standard state
			of the AP is enabled,

			A value of 'false' denotes that the Pre-Standard state
			of the AP is disabled"
	       ::= {  cLApEntry 23 }

	cLApPwrInjectorStateEnabled OBJECT-TYPE
	       SYNTAX      TruthValue
	       MAX-ACCESS  read-write
	       STATUS      current
	       DESCRIPTION
		"This object represents whether the Power Injector state
			of the AP is enabled or disabled.

			A value of 'true' denotes that the Power Injector state
			of the AP is enabled,

			A value of 'false' denotes that the Power Injector state
			of the AP is disabled"
	       ::= {  cLApEntry 24 }

	cLApPwrInjectorSelection OBJECT-TYPE
	    SYNTAX          INTEGER  {
	      unknown(1),
	      installed(2),
	      override(3)
	    }
	       MAX-ACCESS  read-write
	       STATUS      current
	       DESCRIPTION
		"This object specifies the Power Injector selection
			value of the AP.

		'unknown'   - is returned if 
			      'cLApPwrInjectorStateEnabled'is set to false.
		'installed' - configure the MAC address of the 
			      switch port that has a Power Injector.
		'override'  - override the safety checks and assume 
			      a Power Injector is always installed." 
	       ::= {  cLApEntry 25 }

	cLApPwrInjectorSwMacAddr OBJECT-TYPE
	       SYNTAX      MacAddress
	       MAX-ACCESS  read-write
	       STATUS      current
	       DESCRIPTION
		"This object represents the Mac address of the
		switch port that has a power Injector and is 
		valid only when the 'cLApPwrInjectorSelection' 
		is in 'installed' mode.
		if SET to 00:00:00:00:00:00, AP will detect the 
		MAC address of the current switch port that has 
		a Power Injector" 
	       ::= {  cLApEntry 26 }

	cLApWipsEnable OBJECT-TYPE
		 SYNTAX     TruthValue
		 MAX-ACCESS read-write
		 STATUS     deprecated
		 DESCRIPTION
			 "This object represents if this AP is used
			 as WIPS AP.
			 A value of 'true' indicates that this AP is
			 a WIPS AP.
			 A value of 'false' indicates that this AP is
			 not a WIPS AP. This applies only when the 
			 AP is either in local or monitor mode."
		 DEFVAL  { false }
		 ::= { cLApEntry 27 }

	cLApMonitorModeOptimization OBJECT-TYPE
	       SYNTAX      INTEGER {
			      all(1),
			      tracking(2),
			      wips(3),
			      none(4)
		}
	       MAX-ACCESS  read-write
	       STATUS      current
	       DESCRIPTION
		       "This object represents the monitor mode optimization
			on this device.
			    all      - All optimization is enabled 
			    tracking - Tracking is optimized 
			    wips     - WIPS optimization is enabled
			    none     - No optimization is enabled"

	       ::= {  cLApEntry 28 }

	cLApDomainName OBJECT-TYPE
	       SYNTAX SnmpAdminString
	       MAX-ACCESS read-write
	       STATUS current 
	       DESCRIPTION
		"This represents the domain, to which the AP belongs.
			This attribute can be configured only if the static IP
			option is turned on in the AP."
	       ::= { cLApEntry 29 }

	cLApNameServerAddressType OBJECT-TYPE
	       SYNTAX InetAddressType
	       MAX-ACCESS read-write
	       STATUS current
	       DESCRIPTION
		       "This represents the type of the IP address of the 
		name server, made available through cLApNameServerAddress." 
	       ::= { cLApEntry 30 }
	       
	cLApNameServerAddress OBJECT-TYPE
	       SYNTAX InetAddress
	       MAX-ACCESS read-write
	       STATUS current
	       DESCRIPTION
		       "This represents the IP Address of the name server. 
			This attribute can be configured only if the static IP
			option is turned on in the AP."
	       ::= { cLApEntry 31 }

	cLApAMSDUEnable OBJECT-TYPE
		SYNTAX      TruthValue
		MAX-ACCESS  read-write
		STATUS      current
		DESCRIPTION
		"This object specifies the AMSDU status.
		A value of 'true' turns on the AMSDU.
		A value of 'false' turns off the AMSDU."
		DEFVAL  { false }
		::= { cLApEntry 32 }
		
	cLApEncryptionSupported OBJECT-TYPE
		 SYNTAX     TruthValue
		 MAX-ACCESS read-write
		 STATUS     current
		 DESCRIPTION
			"This object specifies whether AP Supports
			 DTLS encryption.                 
		A value of 'true' indicates encryption is supported.
		A value of 'false' indicates encryption is not supported."
		 DEFVAL  { false }
		 ::= { cLApEntry 33 }

	cLApRogueDetectionEnabled OBJECT-TYPE
		 SYNTAX     TruthValue
		 MAX-ACCESS read-write
		 STATUS     current
		 DESCRIPTION
			 "This object specifies whether Rogue Detection
			 is enabled in this AP.                 
			 A value of 'true' enables Rogue Detection.
			 A value of 'false' disables Rogue Detection.
			 Rogue detection is not supported on sniffer 
			 and rogue detector mode APs."
		 DEFVAL  { false }
		 ::= { cLApEntry 34 }

	cLApTcpMss OBJECT-TYPE
			 SYNTAX		INTEGER (0 | 536..1363)
			 MAX-ACCESS	read-write
			 STATUS		current
			 DESCRIPTION
					"This object specifies the TCP Maximum Segment Size 
					for this AP.
					Permissible value are between 536 and 1363. This will
					also enable the TCP MSS flag for this AP.
					Value of 0 will disable the TCP MSS flag for this AP.
					Any change of value for cLApGlobalTcpMss will be 
					reflected to this object. 
					Value for this object can be change only when value of 
					cLApGlobalTcpMss is set as 0."
			 ::= {cLApEntry 35 }

	cLApDataEncryptionStatus OBJECT-TYPE
			SYNTAX		TruthValue
			MAX-ACCESS	read-only
			STATUS		current
			DESCRIPTION
					"This object specifies the data encryption  
			status of AP.
			
			A value of 'true' means data is encrypted between
					AP and WLC.
			
			A value of 'false' means data is Plain Text between
					AP and WLC."
			DEFVAL	{ false }
			::=		{ cLApEntry 36 }

	 cLApNsiKey OBJECT-TYPE
		 SYNTAX     DisplayString (SIZE(0..32))     
			 MAX-ACCESS read-only
			 STATUS		current
			 DESCRIPTION
					"This object specifies the Network Spectrum Interface Key 
			used when the AP is in Spectrum Expert Only Monitor Mode
		(SOMM).This object returns a non-zero value only when the 
			AP is SOMM mode."
			 ::= {cLApEntry 37 }

	cLApAdminStatus OBJECT-TYPE
		 SYNTAX     TruthValue
		 MAX-ACCESS read-write
		 STATUS     current
		 DESCRIPTION
			 "This object specifies the Admin State of the AP,
			 A value of 'true' enables the Admin State.
			 A value of 'false' disables the Admin State."
		 DEFVAL  { false }
		 ::= { cLApEntry 38 }

	cLApPortNumber OBJECT-TYPE
		SYNTAX          InetPortNumber
		MAX-ACCESS read-only
		STATUS     current
		DESCRIPTION
			"This object specifies the port number on which
			 the AP's traffic is coming through." 
		::= { cLApEntry 39 }

	cLApRetransmitCount OBJECT-TYPE
	       SYNTAX      Unsigned32 
	       UNITS       "retries"
	       MAX-ACCESS  read-write
	       STATUS      current
	       DESCRIPTION
		"This object specifies the retransmission count for the Access
		Point Control Packet.This value represents the number of packets
		retransmitted after which the Access Point falls back to another
		controller in case of failover.
		The global retransmit parameters are applicable for all Access 
		Points within a controller. The individual paramters per Access 
		Point, if configured takes precedence over the global values. 
		If an AccessPoint falls back from another controller(in case of
		failover), the values at the AP level has more precedence over 
		the global values in the controller with which it has joined." 
		::= { cLApEntry 40 }

	cLApRetransmitTimeout OBJECT-TYPE
	       SYNTAX      Unsigned32 
	       UNITS       "seconds"
	       MAX-ACCESS  read-write
	       STATUS      current
	       DESCRIPTION
		"This object specifies the retransmission timeout for the Access
		Point Control packet. This value represents the timeout for each
		retransmission, during the fallback of Access Point to another 
		controller in case of failover.
		The global retransmit parameters are applicable for all Access 
		Points within a controller. The individual paramters per Access
		Point, if configured takes precedence over the global values. 
		If an AccessPoint falls back from another controller(in case of
		failover), the values at the AP level has more precedence over 
		the global values in the controller with which it has joined." 
	       ::= { cLApEntry 41 }

	cLApVenueConfigVenueGroup OBJECT-TYPE
	    SYNTAX          INTEGER  {
				unspecified(1),
				assembly(2),
				business(3),
				educational(4),
				factoryAndIndustrial(5),
				institutional(6),
				mercantile(7),
				residential(8),
				storage(9),
				utilityAndMisc(10),
				vehicular(11),
				outdoor(12)
			    }
	    MAX-ACCESS      read-write
	    STATUS          current
	    DESCRIPTION
		"This object indicates the venue group
		for this WLAN."
	    DEFVAL          { unspecified }
	    ::= { cLApEntry 42 }

	cLApVenueConfigVenueType OBJECT-TYPE
	    SYNTAX          INTEGER  {
				unspecified(1),
				unspecifiedAssembly(2),
				arena(3),
				stadium(4),
				passengerTerminal(5),
				amphitheater(6),
				amusementPark(7),
				placeOfWorship(8),
				conventionCenter(9),
				library(10),
				museum(11),
				restaurant(12),
				theater(13),
				bar(14),
				coffeeShop(15),
				zooOrAquarium(16),
				emergencyCoordinationCenter(17),
				unspecifiedBusiness(18),
				doctorOrDentistOffice(19),
				bank(20),
				fireStation(21),
				policeStation(22),
				postOffice(23),
				professionalOffice(24),
				researchAndDevelopmentFacility(25),
				attorneyOffice(26),
				unspecifiedEducational(27),
				schoolPrimary(28),
				schoolSecondary(29),
				universityOrCollege(30),
				unspecifiedFactoryAndIndustrial(31),
				factory(32),
				unspecifiedInstitutional(33),
				hospital(34),
				longTermCareFacility(35),
				alcoholAndDrugRehabilitationCenter(36),
				groupHome(37),
				prisonOrJail(38),
				unspecifiedMercantile(39),
				retailStore(40),
				groceryMarket(41),
				atomotiveServiceStation(42),
				shoppingMall(43),
				gasStation(44),
				unspecifiedResidential(45),
				privateResidence(46),
				hotelOrMotel(47),
				dormitory(48),
				boardingHouse(49),
				unspecifiedStorage(50),
				unspecifiedUtility(51),
				unspecifiedVehicular(52),
				automobileOrTruck(53),
				airplane(54),
				bus(55),
				ferry(56),
				shipOrBoat(57),
				train(58),
				motorBike(59),
				unspecifiedOutdoor(60),
				muniMeshNetwork(61),
				cityPark(62),
				restArea(63),
				trafficControl(64),
				busStop(65),
				kiosk(66)
			    }
	    MAX-ACCESS      read-write
	    STATUS          current
	    DESCRIPTION
		"This object indicates the venue type within
		a particular venue group,for this WLAN.
	    The Venue group-Venue Type relationship is per
		    the following table:
		    Venue Group Venue Type Code Venue Description
		    =========== =============== =================
			 0            0         Unspecified
			 0            1-255     Reserved
			 1            0         Unspecified Assembly
			 1            1         Arena
			 1            2         Stadium
			 1            3         Passenger Terminal (e.g.,
						airport, port, bus station, ferry
						terminal, train station)
			 1            4         Amphitheater
			 1            5         Amusement Park
			 1            6         Place of Worship
			 1            7         Convention Center
			 1            8         Library
			 1            9         Museum
			 1            10        Restaurant
			 1            11        Theater
			 1            12        Bar
			 1            13        Coffee Shop
			 1            14        Zoo or Aquarium
			 1            15        Emergency Coordination Center
			 1            16-255    Reserved
			 2            0         Unspecified Business
			 2            1         Doctor or Dentist office
			 2            2         Bank
			 2            3         Fire Station
			 2            4         Police Station
			 2            6         Post Office
			 2            7         Professional Office
			 2            8         Research and Development Facility
                 2            9         Attorney Office
                 2            10-255    Reserved
                 3            0         Unspecified Educational
                 3            1         School, Primary
                 3            2         School, Secondary
                 3            3         University or College
                 3            4-255     Reserved
                 4            0         Unspecified Factory and Industrial
                 4            1         Factory
                 4            2-255     Reserved
                 5            0         Unspecified Institutional
                 5            1         Hospital
                 5            2         Long-Term Care Facility (e.g.,
                                        Nursing home, Hospice, etc.)
                 5            3         Alcohol and Drug Re-habilitation
                                        Center
                 5            4         Group Home
                 5            5         Prison or Jail
                 5            6-255     Reserved
                 6            0         Unspecified Mercantile
                 6            1         Retail Store
                 6            2         Grocery Market
                 6            3         Automotive Service Station
                 6            4-255     Reserved
                 7            0         Unspecified Residential
                 7            1         Hotel or Motel
                 7            2         Dormitory
                 7            3         Boarding House
                 7            4-255     Reserved
                 8            0-255     Reserved
                 9            0-255     Reserved
                10           0         Unspecified Vehicular
                10           1         Automobile or Truck
                10           2         Airplane
                10           3         Bus
                10           4         Ferry
                10           5         Ship or Boat
                10           6         Train
                10           7-255     Reserved
                11           0         Unspecified Outdoor
                11           1         Muni-mesh Network
                11           2         City Park
                11           3-255     Reserved"
    DEFVAL          { unspecified }
    ::= { cLApEntry 43 }

cLApVenueConfigVenueName OBJECT-TYPE
    SYNTAX          SnmpAdminString 
    MAX-ACCESS      read-write
    STATUS          current
    DESCRIPTION
        "This is the venue name defined for this AP Group."
    ::= { cLApEntry 44 }

cLApVenueConfigLanguage OBJECT-TYPE
    SYNTAX          SnmpAdminString 
    MAX-ACCESS      read-write
    STATUS          current
    DESCRIPTION
        "This is the Language defined for this AP Group."
    ::= { cLApEntry 45 }

cLApLEDState OBJECT-TYPE
       SYNTAX      TruthValue 
       MAX-ACCESS  read-write
       STATUS      current
       DESCRIPTION
          "This object specifies whether the LED state of this access point 
          should be enabled or disabled."
       ::= { cLApEntry 46 }

cLApTrunkVlan OBJECT-TYPE
       SYNTAX      Unsigned32
       MAX-ACCESS read-write
       STATUS      current
       DESCRIPTION
          "This object specifies the trunk VLAN ID
           assigned to this AP's Ethernet interface.
           When a non-zero value is assigned for this
           Object, the management packets will be 
           Tagged with this VLAN ID. When the value of
           Trunk VLAN ID is zero, the packets will be untagged"
       ::= { cLApEntry 47 }

cLApTrunkVlanStatus OBJECT-TYPE
       SYNTAX      TruthValue
       MAX-ACCESS read-only
       STATUS      current
       DESCRIPTION
          "This object specifies whether the trunk VLAN ID
           assigned to this AP's is effective. If the AP is unable
           to route the management frames through the trunk
           vlan, it will revert back to untagged mode. A value of  
           true indicates that the configured trunk VLAN has taken
           effect and  a value of false indicates that the management
           packets will be untagged"
       ::= { cLApEntry 48 }

cLApLocation OBJECT-TYPE
    SYNTAX          SnmpAdminString
    MAX-ACCESS      read-write
    STATUS          current
    DESCRIPTION
        "This object specifies the user specified location of this AP.
         While configuring AP, user should specify a location for
         the AP so that its easy to figure out for some one where
         the AP is located."
    ::= { cLApEntry 49 }


cLApSubMode OBJECT-TYPE
         SYNTAX     INTEGER {
                     none(1),
                     wips(2),
                     pppoe(3),
                     pppoeWips(4)
		     }
         MAX-ACCESS read-write
         STATUS     current
         DESCRIPTION
                 "This object specifies the sub mode of the AP.
                 The option 'wips' applies only when the
		 AP is in local, flexConnect or monitor mode. 
		 This 'pppoe' options apply only when the 
                 AP is in flexConnect mode."
         DEFVAL  { none }
         ::= { cLApEntry 50 }

cLApAssocCount OBJECT-TYPE
       SYNTAX      Unsigned32 
       MAX-ACCESS  read-only
       STATUS      current
       DESCRIPTION
          "This object specifies the association count for the Access Point.
           This counter includes both successful and failed associate attempts,
           but does NOT include the re-associate attempts."
        ::= { cLApEntry 51 }

cLApAssocFailResourceCount OBJECT-TYPE
       SYNTAX      Unsigned32 
       MAX-ACCESS  read-only
       STATUS      current
       DESCRIPTION
          "This object specifies the association failure count for the Access Point due
           to the resource limits, i.e. the max clients of the WLAN/Radio is reached."
        ::= { cLApEntry 52 }

cLApRealTimeStatsModeEnabled OBJECT-TYPE
       SYNTAX      TruthValue 
       MAX-ACCESS  read-write
       STATUS      current
       DESCRIPTION
          "This object specifies whether currently stats mode is 'realtime'.
           There are two stats-mode, realtime and normal, that specifies the
           stats-timer range to be 10-180 sec and 2-5 sec each. Set to TRUE
           if current mode is realtime."
       DEFVAL  { false }
       ::= { cLApEntry 53 }

cLApAssociatedClientCount OBJECT-TYPE
       SYNTAX      Unsigned32 
       MAX-ACCESS  read-only
       STATUS      current
       DESCRIPTION
          "This object specifies the associated client number for the Access Point."
        ::= { cLApEntry 54 }

 
cLApMemoryCurrentUsage OBJECT-TYPE
       SYNTAX       Unsigned32
       MAX-ACCESS   read-only
       STATUS       current
       DESCRIPTION
          "This object specifies the percent of current memory usage 
           of the access point."
       ::= { cLApEntry 55 }
 
cLApMemoryAverageUsage OBJECT-TYPE
       SYNTAX       Unsigned32
       MAX-ACCESS   read-only
       STATUS       current
       DESCRIPTION
          "This object specifies the percent of average memory usage
           of the access point. The statistics window is defined by
           clsSysStatisticsInterval."
       ::= { cLApEntry 56 }

cLApCpuCurrentUsage OBJECT-TYPE
       SYNTAX       Unsigned32
       MAX-ACCESS   read-only
       STATUS       current
       DESCRIPTION
          "This object specifies the percent of current CPU usage
           of the access point."
       ::= { cLApEntry 57 }
 
cLApCpuAverageUsage OBJECT-TYPE
       SYNTAX       Unsigned32
       MAX-ACCESS   read-only
       STATUS       current
       DESCRIPTION
          "This object specifies the percent of average CPU usage
           of the access point. The statistics window is defined by
           clsSysStatisticsInterval."
       ::= { cLApEntry 58 }

cLApUpgradeFromVersion OBJECT-TYPE
        SYNTAX     DisplayString
        MAX-ACCESS read-only
        STATUS     current
        DESCRIPTION
                "This object specifies the AP image upgrade
		 from version." 
        ::= { cLApEntry 59 }

cLApUpgradeToVersion OBJECT-TYPE
        SYNTAX     DisplayString
        MAX-ACCESS read-only
        STATUS     current
        DESCRIPTION
                "This object specifies the AP image upgrade
		 to version." 
        ::= { cLApEntry 60 }

cLApUpgradeFailureCause OBJECT-TYPE
        SYNTAX     DisplayString
        MAX-ACCESS read-only
        STATUS     current
        DESCRIPTION
                "This object specifies the cause of the
		 AP image upgrade failure." 
        ::= { cLApEntry 61 }

cLApMaxClientLimitNumberTrap OBJECT-TYPE
        SYNTAX     Unsigned32
        MAX-ACCESS read-only
        STATUS     current
        DESCRIPTION
                "This object specifies the max client limit number." 
        ::= { cLApEntry 62 }

cLApMaxClientLimitCause OBJECT-TYPE
        SYNTAX     DisplayString
        MAX-ACCESS read-only
        STATUS     current
        DESCRIPTION
                "This object specifies the cause of the
        max client limit reach." 
        ::= { cLApEntry 63 }

cLApMaxClientLimitSet OBJECT-TYPE
        SYNTAX     TruthValue
        MAX-ACCESS read-only
        STATUS     current
        DESCRIPTION
                "This object specifies whether this event is
       raised or cleared.
         'TRUE' indicates this event is set.
         'FALSE' indicates this even is cleared." 
        ::= { cLApEntry 64 }

cLApFloorLabel OBJECT-TYPE
       SYNTAX      Unsigned64
       MAX-ACCESS  read-write
       STATUS      current
       DESCRIPTION
          "This object specifies the floor label for the Access Point."
        ::= { cLApEntry 65 }
 
cLApConnectCount  OBJECT-TYPE
       SYNTAX      Unsigned32
 	   MAX-ACCESS  read-only
 	   STATUS      current
 	   DESCRIPTION
 	       "This object specifies the Count of AP's that are connected to the Controller."
        ::= { cLApEntry 66 }		   

cLApReassocSuccCount OBJECT-TYPE
        SYNTAX      Counter32
        MAX-ACCESS  read-only
        STATUS      current
        DESCRIPTION
                "This object specifies the successful re-association
                 count for the Access Point."
        ::= { cLApEntry 67 }

cLApReassocFailCount OBJECT-TYPE
        SYNTAX      Counter32
        MAX-ACCESS  read-only
        STATUS      current
        DESCRIPTION
                "This object specifies the failed re-association
                 count for the Access Point."
        ::= { cLApEntry 68 }

cLAdjChannelRogueEnabled OBJECT-TYPE
       SYNTAX     TruthValue
       MAX-ACCESS read-write
       STATUS     current
       DESCRIPTION
           "This object specifies If Rogue AP
            Detection and Removed Traps need to be sent.
            A value of true enables Adj Rogue Detection.
            A value of false disables Adj Rogue Detection.
            To Enable this trap it is requested to disable the
            bsnRogueAPTrapEnable in order to avoid the duplicates."
       ::= { cLApEntry 69 }			

cLApAssocFailCountByRate OBJECT-TYPE
        SYNTAX      Unsigned32
        MAX-ACCESS  read-only
        STATUS      current
        DESCRIPTION
                "This object specifies the failed association
                 count for the Access Point caused by rate mismatch."
        ::= { cLApEntry 70 }

cLApAbnormalOfflineCount OBJECT-TYPE
       SYNTAX      Unsigned32 
       MAX-ACCESS  read-only
       STATUS      current
       DESCRIPTION
          "This object specifies the abnormal offline count for the Access Point."
        ::= { cLApEntry 71 }

cLApActiveClientCount OBJECT-TYPE
       SYNTAX      Unsigned32 
        MAX-ACCESS  read-only
        STATUS      current
        DESCRIPTION
           "This object specifies the active client number for the Access Point."
        ::= { cLApEntry 72 }

cLApAssocFailCountForRssiLow OBJECT-TYPE
        SYNTAX      Unsigned32
        MAX-ACCESS  read-only
        STATUS      current
        DESCRIPTION
                "This object specifies the failed association
                 count for the Access Point caused by RSSI low."
        ::= { cLApEntry 73 }

cLApSysNetId OBJECT-TYPE
        SYNTAX SnmpAdminString
        MAX-ACCESS read-write
        STATUS current
        DESCRIPTION
           "This object specifies the ApSysNetId which is the numeric string
             to identify the system information like ApName."
        ::= {  cLApEntry 74 }

cLApAssocFailTimes OBJECT-TYPE
        SYNTAX      Counter32
        MAX-ACCESS  read-only
        STATUS      current
        DESCRIPTION
           "This object specifies the counts of client failed association to the Access Point."
        ::= { cLApEntry 75 }
      
cLApAntennaBandMode OBJECT-TYPE
        SYNTAX      INTEGER{
                      notApplicable(1),
                             single(2),
                               dual(3)
                    }
        MAX-ACCESS  read-write
        STATUS      current
        DESCRIPTION
           "This object specifies the mode of Antenna band. For 
           access points, in which this variable is not relevant,
           value of 'notApplicable' will be returned.
           In the dual band mode, only two dual band antennas are used, 
           connected to ports 1 and 2. In this case, both bands share 
           these antennas."
        ::= { cLApEntry 76 }
      

cLApHeartBeatRspAvgTime OBJECT-TYPE
        SYNTAX     INTEGER(1..100000)
        UNITS      "milliseconds"
        MAX-ACCESS  read-only
        STATUS      current
        DESCRIPTION
            "This object indicates the average interval between sending the echo request
            and receiving the echo response in AP."
        ::= { cLApEntry 77 }

cLApEchoRequestCount OBJECT-TYPE
        SYNTAX      Counter32
        MAX-ACCESS  read-only
        STATUS      current
        DESCRIPTION
             "This object indicates the Echo Request packet
             count sent from AP to Access Controller."
        ::= { cLApEntry 78 }

cLApEchoResponseLossCount OBJECT-TYPE
        SYNTAX      Counter32
        MAX-ACCESS  read-only
        STATUS      current
        DESCRIPTION
             "This object indicates the Echo Response Loss
             count from Access Controller to AP."
        ::= { cLApEntry 79 }

cLApModuleInserted OBJECT-TYPE
       SYNTAX      DisplayString
       MAX-ACCESS  read-only
       STATUS      current
       DESCRIPTION
              "This object represents the type of the module 
               inserted in to the AP."
        ::= { cLApEntry 80 }

cLApEnableModule OBJECT-TYPE
       SYNTAX      TruthValue
       MAX-ACCESS  read-write
       STATUS      current
       DESCRIPTION
             "This object specifies the status of the external
              module .
              enable(1) - enable the module,
              disable(0) - disables the module."
        ::= { cLApEntry 81 }

cLApIsUniversal OBJECT-TYPE
       SYNTAX      TruthValue
       MAX-ACCESS  read-only
       STATUS      current
       DESCRIPTION
              "This object represents the if the AP is 
               universal AP. A value true will be returned if the AP is a Universal SKU based AP. 
               A value false will be returned if the AP is a non-Universal SKU AP."
        ::= { cLApEntry 82 }

cLApUniversalPrimeStatus OBJECT-TYPE
       SYNTAX      DisplayString
       MAX-ACCESS  read-only
       STATUS      current
       DESCRIPTION
              "This object represents the method of Priming
              of the Universal AP."
        ::= { cLApEntry 83 }

cLApIsMaster OBJECT-TYPE
       SYNTAX      TruthValue
       MAX-ACCESS  read-only
       STATUS      current
       DESCRIPTION
              "This object represents if the Flex AP is a 
               Master AP. This applies only to FlexExpress controllers. A value true 
               will be returned if the AP is a Master AP. A value false will be returned 
               if its not."
        ::= { cLApEntry 84 }

cLApBleFWDownloadStatus OBJECT-TYPE
       SYNTAX      TruthValue
       MAX-ACCESS  read-only
       STATUS      current
       DESCRIPTION
                 "This object lists out all the APs in which BLE
                Firmware download is in progress."
        ::= {  cLApEntry 85 }

cLApDot11XorDartConnectorStatus OBJECT-TYPE
       SYNTAX      DisplayString
       MAX-ACCESS  read-only
       STATUS      current
       DESCRIPTION
              "This object represents the Xor Dart connector status."
        ::= { cLApEntry 86 }

--********************************************************************
-- *  AP Dot11 Interface Information
--********************************************************************
cLApDot11IfTable OBJECT-TYPE
        SYNTAX SEQUENCE OF CLApDot11IfEntry
        MAX-ACCESS not-accessible
        STATUS     current
        DESCRIPTION
                "This table represents the information about the
                basic functional parameters corresponding to
                the dot11 interfaces of the APs that have joined
                the controller. "
        ::= { ciscoLwappApIf 1 }

cLApDot11IfEntry OBJECT-TYPE
        SYNTAX     CLApDot11IfEntry
        MAX-ACCESS not-accessible
        STATUS     current
        DESCRIPTION
                "An entry in this table represents the 802.11
                functional parameters of the dot11 interface of
                an AP that has joined the controller.

                Entries are added when the APs associate to this
                controller and deleted when they lose their
                association. " 
    INDEX           {
                        cLApSysMacAddress,
                        cLApDot11IfSlotId
                    } 
        ::= { cLApDot11IfTable 1 }

CLApDot11IfEntry ::= SEQUENCE {
                cLApDot11IfSlotId         Unsigned32, 
                cLApDot11IfType           CLApIfType,
                cLApDot11IfRegDomain      DisplayString, 
                cLApDot11nSupport         TruthValue, 
                cLAp11nChannelBandwidth   INTEGER,
                cLApLomEnabled            TruthValue,
                cLApLomFirstChannel       CLDot11Channel,
                cLApLomSecondChannel      CLDot11Channel,
                cLApLomThirdChannel       CLDot11Channel,
                cLApLomFourthChannel      CLDot11Channel,
                cLApExtensionChannel      CLDot11Channel,
                cLApLegacyBeamForming     INTEGER,
                cLApCdpOverAirEnabled     TruthValue,
                cLApDot11IfAdminStatus    TruthValue,
                cLApDot11IfLinkChangeCount Unsigned32,
                cLApDot11MaxClients       Unsigned32,
                cLApPromiscuousModeDwelling   Unsigned32,
                cLApDot11IfStaKeepingTime     TimeTicks,
                cLApDot11IfLinkSpeed          Gauge32,
                cLApDot11IfMtu                Unsigned32,
                cLApDot11IfDesc               SnmpAdminString,
                cLApDot11acSupport        TruthValue,
                cLAp11ChannelBandwidth   INTEGER,
                cLApExtensionChannels      DisplayString,
                cLAPDot11IfMinTxPowerStep   Unsigned32,
                cLApDot11XorRadioMode       INTEGER,
                cLApDot11XorRadioBand       INTEGER,
                cLApDot11XorRadioRoleAssignment INTEGER
        }

cLApDot11IfSlotId OBJECT-TYPE
        SYNTAX     Unsigned32
        MAX-ACCESS not-accessible
        STATUS     current
        DESCRIPTION
                "This object represents the slot ID of a dot11
                interface on an AP. 

                The slot ID for a particular dot11 interface as
                represented by this object ranges from 0 to 
                cLApMaxNumberOfDot11Slots - 1. "
        ::= { cLApDot11IfEntry 1 }

cLApDot11IfType OBJECT-TYPE
        SYNTAX     CLApIfType     
        MAX-ACCESS read-only
        STATUS     current 
        DESCRIPTION
                "This object represents the type of this dot11
                interface. "
        ::= { cLApDot11IfEntry 2 }

cLApDot11IfRegDomain OBJECT-TYPE
        SYNTAX     DisplayString (SIZE(1..255))     
        MAX-ACCESS read-only
        STATUS     current 
        DESCRIPTION
                "This object indicates the regulatory domain for 
                this radio type on this AP."
        ::= { cLApDot11IfEntry 3 }

cLApDot11nSupport OBJECT-TYPE
        SYNTAX     TruthValue
        MAX-ACCESS read-only
        STATUS     current
        DESCRIPTION
                "This objects indicates whether 802.11n support is
                available on this AP."
        ::= { cLApDot11IfEntry 4 }

cLAp11nChannelBandwidth OBJECT-TYPE
        SYNTAX     INTEGER {
                   five(1),
                   ten(2),
                   twenty(3),
                   forty(4)
               }
        UNITS  "mhz"
        MAX-ACCESS read-write
        STATUS deprecated
        DESCRIPTION
                "This object indicates the channel bandwidth for 
                this AP. This applies to 802.11n networks only.
                This has been deprecated for cLAp11ChannelBandwidth."
        ::= { cLApDot11IfEntry 5 }

cLApLomEnabled OBJECT-TYPE
       SYNTAX      TruthValue
       MAX-ACCESS  read-write
       STATUS      deprecated
       DESCRIPTION
            "This object indicates whether this AP is being monitored 
            by the location server. A value of 'true' indicates that 
            the monitoring is enabled. A value of 'false' indicates 
            that the monitoring is disabled."
         DEFVAL  { false }
        ::= { cLApDot11IfEntry 6 }

cLApLomFirstChannel OBJECT-TYPE
       SYNTAX      CLDot11Channel
       MAX-ACCESS  read-write
       STATUS      current
       DESCRIPTION
              "This object represents the first location channel that is
              being monitored." 
        ::= { cLApDot11IfEntry 7 }

cLApLomSecondChannel OBJECT-TYPE
       SYNTAX      CLDot11Channel
       MAX-ACCESS  read-write
       STATUS      current
       DESCRIPTION
              "This object represents the second location channel that 
              is being monitored." 
        ::= { cLApDot11IfEntry 8 }

cLApLomThirdChannel OBJECT-TYPE
       SYNTAX      CLDot11Channel
       MAX-ACCESS  read-write
       STATUS      current
       DESCRIPTION
        "This object represents the third location
        channel that is being monitored." 
        ::= { cLApDot11IfEntry 9 }

cLApLomFourthChannel OBJECT-TYPE
       SYNTAX      CLDot11Channel
       MAX-ACCESS  read-write
       STATUS      current
       DESCRIPTION
        "This object represents the fourth location
        channel that is being monitored." 
        ::= { cLApDot11IfEntry 10 }

cLApExtensionChannel OBJECT-TYPE
       SYNTAX      CLDot11Channel
       MAX-ACCESS  read-only
       STATUS      deprecated
       DESCRIPTION
              "This object represents the extension channel. This is 
               applicable when the channel bandwidth is set to 40mhz."
        ::= { cLApDot11IfEntry 11 }

cLApLegacyBeamForming OBJECT-TYPE
       SYNTAX      INTEGER {
                   enable(1),
                   disable(2),
                   notApplicable(3)
               } 
       MAX-ACCESS  read-write
       STATUS      deprecated
       DESCRIPTION
            "This object indicates the status of legacy beam forming
            in this AP. This object is applicable only for
            11n supported APs.
            For APs that does not support legacy beam forming,
            a get request on this attribute will return 
            the value 'notApplicable'.
            A value of 'enable' indicates that the legacy
            Beam forming is enabled in this AP. 
            A value of 'false' indicates that the legacy
            Beam forming is disabled in this AP."
    DEFVAL          { notApplicable } 
       ::= { cLApDot11IfEntry 12 }

cLApCdpOverAirEnabled OBJECT-TYPE
       SYNTAX      TruthValue
       MAX-ACCESS  read-write
       STATUS      current
       DESCRIPTION
            "This object indicates the status of Cisco Discovery
            Protocol(CDP) in this interface, represented by
            cLApDot11IfSlotId of the AP, represented by
            cLApSysMacAddress.
            A value of 'true' indicates that CDP is enabled in
            the dot11 interface(s) of this AP.
            A value of 'false' indicates that CDP is disabled in
            the dot11 interface(s) of this AP."
       ::= { cLApDot11IfEntry 13 }

cLApDot11IfAdminStatus OBJECT-TYPE
       SYNTAX      TruthValue
       MAX-ACCESS  read-write
       STATUS      current
       DESCRIPTION
              "This object represents the AP's interface admin
	       status.
	       A value of 'true' indicates admin state as Up.
	       A value of 'false' indicates admin state as Down."
        ::= { cLApDot11IfEntry 14 }

cLApDot11IfLinkChangeCount OBJECT-TYPE
        SYNTAX     Unsigned32
        MAX-ACCESS read-only
        STATUS     current
        DESCRIPTION
                "This object represents the link change count of a dot11
                interface on an AP."  
        ::= { cLApDot11IfEntry 15 }

cLApDot11MaxClients OBJECT-TYPE
        SYNTAX     Unsigned32(1..200)
        MAX-ACCESS read-write
        STATUS     current
        DESCRIPTION
                "This object represents the max supported associated clients
                of a dot11 interface on an AP."  
        DEFVAL{ 200 }
        ::= { cLApDot11IfEntry 16 }

cLApPromiscuousModeDwelling OBJECT-TYPE
       SYNTAX      Unsigned32
       UNITS       "percentage"
       MAX-ACCESS  read-only
       STATUS      current
       DESCRIPTION
          "This object represents the percentage of time for the dot11
           interface of an Access Point spent in promiscuous mode 
           dwelling."
        ::= { cLApDot11IfEntry 17 }

cLApDot11IfStaKeepingTime OBJECT-TYPE
       SYNTAX      TimeTicks
       MAX-ACCESS  read-only
       STATUS      current
       DESCRIPTION
           "This object represents the time in hundredths
            of a second since the last dot11 interface state changed."
        ::= { cLApDot11IfEntry 18 }
        
cLApDot11IfLinkSpeed OBJECT-TYPE
       SYNTAX      Gauge32
       UNITS       "bps"
       MAX-ACCESS  read-only
       STATUS      current
       DESCRIPTION
           "Speed of the interface in units of 1,000,000
            bits per second"
        ::= { cLApDot11IfEntry 19 }
        
cLApDot11IfMtu OBJECT-TYPE
       SYNTAX      Unsigned32
       MAX-ACCESS  read-only
       STATUS      current
       DESCRIPTION
           "This object represents interface's MTU value"
        ::= { cLApDot11IfEntry 20 }

cLApDot11IfDesc OBJECT-TYPE
       SYNTAX      SnmpAdminString
       MAX-ACCESS  read-only
       STATUS      current
       DESCRIPTION
           "This object represents the description of this interface"
        ::= { cLApDot11IfEntry 21 }

cLApDot11acSupport OBJECT-TYPE
        SYNTAX     TruthValue
        MAX-ACCESS read-only
        STATUS     current
        DESCRIPTION
                "This objects indicates whether 802.11ac support is
                available on this AP."
        ::= { cLApDot11IfEntry 22 }

cLAp11ChannelBandwidth OBJECT-TYPE
        SYNTAX     INTEGER {
                   five(1),
                   ten(2),
                   twenty(3),
                   fourty(4),
                   eighty(5),
                   onesixty(6)
               }
        UNITS  "mhz"
        MAX-ACCESS read-write
        STATUS     current
        DESCRIPTION
                "This object indicates the channel bandwidth for 
                this AP. This applies to 802.11n and 802.11ac networks only."
        ::= { cLApDot11IfEntry 23 }

cLApExtensionChannels OBJECT-TYPE
       SYNTAX      DisplayString
       MAX-ACCESS  read-only
       STATUS      current
       DESCRIPTION
              "This object represents the extension channels separated by
              commas. This is applicable when the channel bandwidth is set to 40mhz
              or 80mhz."
        ::= { cLApDot11IfEntry 24 }

cLAPDot11IfMinTxPowerStep OBJECT-TYPE
      SYNTAX         Unsigned32
      UNITS          "dbm"
      MAX-ACCESS     read-only
      STATUS         current
      DESCRIPTION
              "This object represents minimum adjust step of the AP radio TX power.
               The power step is coded as an unsigned integer in units of dbm."
      ::= { cLApDot11IfEntry 25 }

cLApDot11XorRadioMode OBJECT-TYPE
        SYNTAX     INTEGER {
                   servingClients(1),
               	   monitor(2)
               }
        MAX-ACCESS read-write
        STATUS     current
        DESCRIPTION
                "This object helps to set the radio mode for
                the AP which has XOR radio."
        ::= { cLApDot11IfEntry 26 }

cLApDot11XorRadioBand OBJECT-TYPE
        SYNTAX     INTEGER {
                   radioband24G(1),
                   radioband5G(2)
               }
        MAX-ACCESS read-write
        STATUS     current
        DESCRIPTION
                "This object helps to set the radio bandwidth for
                the AP which has XOR radio."
        ::= { cLApDot11IfEntry 27 }    

cLApDot11XorRadioRoleAssignment OBJECT-TYPE
        SYNTAX     INTEGER {
                   auto(1),
                   manual(2)
               }
        MAX-ACCESS read-write
        STATUS     current
        DESCRIPTION
                "This object helps to set the radio role assignment of
                the AP which has XOR radio."
        ::= { cLApDot11IfEntry 28 }

--********************************************************************
-- *  AP Ethernet Interface Information
--********************************************************************
cLApEthernetIfTable OBJECT-TYPE
        SYNTAX SEQUENCE OF CLApEthernetIfEntry
        MAX-ACCESS not-accessible
        STATUS     current
        DESCRIPTION
                "This table represents the information about the
                basic functional parameters corresponding to
                the Ethernet interfaces of the APs that have joined
                the controller. "
        ::= { ciscoLwappApIf 2 }

cLApEthernetIfEntry OBJECT-TYPE
        SYNTAX     CLApEthernetIfEntry
        MAX-ACCESS not-accessible
        STATUS     current
        DESCRIPTION
                "An entry in this table represents the functional
                parameters of the Ethernet interface of an AP that
                has joined the controller.

                Entries are added when the APs associate to this
                controller and deleted when they lose their
                association. " 
    INDEX           {
                        cLApSysMacAddress,
                        cLApEthernetIfSlotId
                    } 
        ::= { cLApEthernetIfTable 1 }

CLApEthernetIfEntry ::= SEQUENCE {
                cLApEthernetIfSlotId       Unsigned32, 
                cLApEthernetIfName         SnmpAdminString,
                cLApEthernetIfMacAddress   MacAddress,
                cLApEthernetIfAdminStatus  INTEGER,
                cLApEthernetIfOperStatus   INTEGER,
                cLApEthernetIfRxUcastPkts  Counter32,
                cLApEthernetIfRxNUcastPkts Counter32,
                cLApEthernetIfTxUcastPkts  Counter32,
                cLApEthernetIfTxNUcastPkts Counter32,
                cLApEthernetIfDuplex       INTEGER,
                cLApEthernetIfLinkSpeed    Gauge32,
                cLApEthernetIfPOEPower     INTEGER,
                cLApEthernetIfRxTotalBytes      Counter32,
                cLApEthernetIfTxTotalBytes      Counter32,
                cLApEthernetIfInputCrc          Counter32,
                cLApEthernetIfInputAborts       Counter32,
                cLApEthernetIfInputErrors       Counter32,
                cLApEthernetIfInputFrames       Counter32,
                cLApEthernetIfInputOverrun      Counter32,
                cLApEthernetIfInputDrops        Counter32,
                cLApEthernetIfInputResource     Counter32,
                cLApEthernetIfUnknownProtocol   Counter32,
                cLApEthernetIfRunts             Counter32,
                cLApEthernetIfGiants            Counter32,
                cLApEthernetIfThrottle          Counter32,
                cLApEthernetIfResets            Counter32,
                cLApEthernetIfOutputCollision   Counter32,
                cLApEthernetIfOutputNoBuffer    Counter32,
                cLApEthernetIfOutputResource    Counter32,
                cLApEthernetIfOutputUnderrun    Counter32,
                cLApEthernetIfOutputErrors      Counter32,
                cLApEthernetIfOutputTotalDrops  Counter32,
                cLApEthernetIfCdpEnabled        TruthValue,
                cLApEthernetIfMtu               Unsigned32, 
                cLApEthernetIfType              IANAifType,
                cLApEthernetIfLinkChangeCount   Counter32
		
        }

cLApEthernetIfSlotId OBJECT-TYPE
        SYNTAX     Unsigned32
        MAX-ACCESS not-accessible
        STATUS     current
        DESCRIPTION
                "This object represents the slot ID of an Ethernet
                interface on an AP. 

                The slot ID for a particular Ethernet interface as
                represented by this object ranges from 0 to 
                cLApMaxNumberOfEthernetSlots - 1."
        ::= { cLApEthernetIfEntry 1 }

cLApEthernetIfName OBJECT-TYPE
        SYNTAX SnmpAdminString (SIZE(0..32))
        MAX-ACCESS read-only
        STATUS current
        DESCRIPTION
        "This object represents the name of the
        Ethernet interface." 
        ::= { cLApEthernetIfEntry 2 }

cLApEthernetIfMacAddress OBJECT-TYPE
        SYNTAX     MacAddress
        MAX-ACCESS read-only
        STATUS     current
        DESCRIPTION
        "This object represents MAC address of the Ethernet
        interface in the slot represented by 
        cLApEthernetIfSlotId." 
        ::= { cLApEthernetIfEntry 3 }

cLApEthernetIfAdminStatus OBJECT-TYPE
    SYNTAX          INTEGER  {
                        up(1),
                        down(2)
                    }
        MAX-ACCESS read-write
        STATUS     current
        DESCRIPTION
                "This object represents the admin state of the physical
                 Ethernet interface on the AP."
        ::= { cLApEthernetIfEntry 4 }

cLApEthernetIfOperStatus OBJECT-TYPE
    SYNTAX          INTEGER  {
                        up(1),
                        down(2)
                    }
        MAX-ACCESS read-only
        STATUS     current
        DESCRIPTION
        "This object represents the operational state
        of the physical Ethernet interface on the AP." 
        ::= { cLApEthernetIfEntry 5 }

cLApEthernetIfRxUcastPkts OBJECT-TYPE
        SYNTAX     Counter32
        UNITS      "packets"
        MAX-ACCESS read-only
        STATUS     current
        DESCRIPTION
                "This object represents total number of unicast packets 
                received on the interface."
        ::= { cLApEthernetIfEntry 6 }

cLApEthernetIfRxNUcastPkts OBJECT-TYPE
        SYNTAX      Counter32
        UNITS       "packets"
        MAX-ACCESS  read-only
        STATUS      current
        DESCRIPTION
                "This object represents total number of non-unicast or
        multicast packets received on the interface" 
        ::= { cLApEthernetIfEntry 7 }

cLApEthernetIfTxUcastPkts OBJECT-TYPE
        SYNTAX     Counter32
        UNITS      "packets"
        MAX-ACCESS read-only
        STATUS     current
        DESCRIPTION
                "This object represents total number of unicast packets 
                transmitted on the interface."
        ::= { cLApEthernetIfEntry 8 }

cLApEthernetIfTxNUcastPkts OBJECT-TYPE
        SYNTAX     Counter32
        UNITS      "packets"
        MAX-ACCESS read-only
        STATUS     current
        DESCRIPTION
                "This object represents total number of non-unicast or
        multicast packets transmitted on the interface" 
        ::= { cLApEthernetIfEntry 9 }

cLApEthernetIfDuplex OBJECT-TYPE
        SYNTAX     INTEGER {
            unknown(1),
            halfduplex(2),
            fullduplex(3),
            auto(4)
        }
        MAX-ACCESS read-only
        STATUS     current
        DESCRIPTION
                "This object represents interface's duplex mode"
        ::= { cLApEthernetIfEntry 10 }

cLApEthernetIfLinkSpeed OBJECT-TYPE
        SYNTAX     Gauge32
        MAX-ACCESS read-only
        STATUS     current
        DESCRIPTION
        "Speed of the interface in units of 1,000,000
        bits per second" 
        ::= { cLApEthernetIfEntry 11 }

cLApEthernetIfPOEPower OBJECT-TYPE
        SYNTAX     INTEGER {
            none(1),
            drawn(2),
            notdrawn(3)
        }
        MAX-ACCESS read-only
        STATUS     current
        DESCRIPTION
          "This object represents whether this interface supports
          Power Over Ethernet (POE)
          none     - POE is not supported
          drawn    - This interface supports POE, and power is
                     being drawn
          notdrawn - POE power is not drawn"
        ::= { cLApEthernetIfEntry 12 }

cLApEthernetIfRxTotalBytes OBJECT-TYPE
        SYNTAX     Counter32
        UNITS      "Bytes"
        MAX-ACCESS read-only
        STATUS     current
        DESCRIPTION
            "This object represents total number of bytes in the 
            error-free packets received on the interface."
        ::= { cLApEthernetIfEntry 13 }
       
cLApEthernetIfTxTotalBytes OBJECT-TYPE
        SYNTAX     Counter32
        UNITS      "Bytes"
        MAX-ACCESS read-only
        STATUS     current
        DESCRIPTION
            "This object represents total number of bytes in the
            error-free packets transmitted on the interface."
        ::= { cLApEthernetIfEntry 14 }

cLApEthernetIfInputCrc OBJECT-TYPE
        SYNTAX     Counter32
        UNITS      "packets"
        MAX-ACCESS read-only
        STATUS     current
        DESCRIPTION
            "This object represents total number of CRC error in
            packets received on the interface."
       ::= { cLApEthernetIfEntry 15 }

cLApEthernetIfInputAborts OBJECT-TYPE
        SYNTAX     Counter32
        UNITS      "packets"
        MAX-ACCESS read-only
        STATUS     current
        DESCRIPTION
            "This object represents total number of packet aborted 
            while receiving on the interface."
        ::= { cLApEthernetIfEntry 16 }

cLApEthernetIfInputErrors OBJECT-TYPE
        SYNTAX     Counter32
        UNITS      "packets"
        MAX-ACCESS read-only
        STATUS     current
        DESCRIPTION
            "This object represents sum of all errors in the packets
            while receiving on the interface."
        ::= { cLApEthernetIfEntry 17 }

cLApEthernetIfInputFrames OBJECT-TYPE
        SYNTAX     Counter32
        UNITS      "packets"
        MAX-ACCESS read-only
        STATUS     current
        DESCRIPTION
            "This object represents total number of packet received 
            incorrectly having a CRC error and a noninteger number 
            of octets on the interface."
        ::= { cLApEthernetIfEntry 18 }

cLApEthernetIfInputOverrun OBJECT-TYPE
        SYNTAX     Counter32
        UNITS      "packets"
        MAX-ACCESS read-only
        STATUS     current
        DESCRIPTION
            "This object represents the number of times the receiver
            hardware was incapable of handing received data to a 
            hardware buffer because the input rate exceeded the 
            receiver's capability to handle the data."
       ::= { cLApEthernetIfEntry 19 }

cLApEthernetIfInputDrops OBJECT-TYPE
        SYNTAX     Counter32
        UNITS      "packets"
        MAX-ACCESS read-only
        STATUS     current
        DESCRIPTION
            "This object represents total number of packets dropped
        while receiving on the interface because the queue 
        was full." 
        ::= { cLApEthernetIfEntry 20 }

cLApEthernetIfInputResource OBJECT-TYPE
        SYNTAX     Counter32
        UNITS      "packets"
        MAX-ACCESS read-only
        STATUS     current
        DESCRIPTION
            "This object represents total number of resource errors in
            packets received on the interface."
        ::= { cLApEthernetIfEntry 21 }
                                                                   
cLApEthernetIfUnknownProtocol OBJECT-TYPE
        SYNTAX     Counter32
        UNITS      "packets"
        MAX-ACCESS read-only
        STATUS     current
        DESCRIPTION
            "This object represents total number of packet discarded on
            the interface due to unknown protocol."
        ::= { cLApEthernetIfEntry 22 }

cLApEthernetIfRunts OBJECT-TYPE
        SYNTAX     Counter32
        UNITS      "packets"
        MAX-ACCESS read-only
        STATUS     current
        DESCRIPTION
        "This object represents number of packets that
        are discarded because they are smaller than the 
        medium's minimum packet size." 
        ::= { cLApEthernetIfEntry 23 }

cLApEthernetIfGiants OBJECT-TYPE
        SYNTAX     Counter32
        UNITS      "packets"
        MAX-ACCESS read-only
        STATUS     current
        DESCRIPTION
        "This object represents number of packets that
        are discarded because they exceed the medium's 
        maximum packet size." 
          ::= { cLApEthernetIfEntry 24 }
                                                                                                                          
cLApEthernetIfThrottle OBJECT-TYPE
        SYNTAX     Counter32
        MAX-ACCESS read-only
        STATUS     current
        DESCRIPTION
        "This object represents total number of times the
        interface advised a sending NIC that it was 
        overwhelmed by packets being sent and to slow the 
        pace of delivery." 
        ::= { cLApEthernetIfEntry 25 }

cLApEthernetIfResets OBJECT-TYPE
        SYNTAX     Counter32
        MAX-ACCESS read-only
        STATUS     current
        DESCRIPTION
        "This object represents number of times that an
        interface has been completely reset." 
        ::= { cLApEthernetIfEntry 26 }

cLApEthernetIfOutputCollision OBJECT-TYPE
        SYNTAX     Counter32
        UNITS      "packets"
        MAX-ACCESS read-only
        STATUS     current
        DESCRIPTION
            "This object represents total number of packet
            retransmitted due to an Ethernet collision."
        ::= { cLApEthernetIfEntry 27 }

cLApEthernetIfOutputNoBuffer OBJECT-TYPE
        SYNTAX     Counter32
        UNITS      "packets"
        MAX-ACCESS read-only
        STATUS     current
        DESCRIPTION
            "This object represents total number of packets discarded 
            because there was no buffer space."
        ::= { cLApEthernetIfEntry 28 }

cLApEthernetIfOutputResource OBJECT-TYPE
        SYNTAX     Counter32
        UNITS      "packets"
        MAX-ACCESS read-only
        STATUS     current
        DESCRIPTION
            "This object represents total number of resource 
            errors in packets transmitted on the interface."
        ::= { cLApEthernetIfEntry 29 }

cLApEthernetIfOutputUnderrun OBJECT-TYPE
        SYNTAX     Counter32
        UNITS      "packets"
        MAX-ACCESS read-only
        STATUS     current
        DESCRIPTION
            "This object represents the number of times the transmitter 
            has been running faster than the router can handle."
        ::= { cLApEthernetIfEntry 30 }

cLApEthernetIfOutputErrors OBJECT-TYPE
        SYNTAX     Counter32
        UNITS      "packets"
        MAX-ACCESS read-only
        STATUS     current
        DESCRIPTION
            "This object represents sum of all errors that prevented 
            the final transmission of packets out of the interface."
        ::= { cLApEthernetIfEntry 31 }

cLApEthernetIfOutputTotalDrops OBJECT-TYPE
        SYNTAX     Counter32
        UNITS      "packets"
        MAX-ACCESS read-only
        STATUS     current
        DESCRIPTION
            "This object represents total number of packets dropped
        while transmitting from the interface because the queue 
        was full." 
        ::= { cLApEthernetIfEntry 32 }        

cLApEthernetIfCdpEnabled OBJECT-TYPE
       SYNTAX      TruthValue
       MAX-ACCESS  read-write
       STATUS      current
       DESCRIPTION
            "This object indicates the status of Cisco Discovery
            Protocol(CDP) in this interface represented by
            cLApEthernetIfSlotId of the AP represented by
            cLApSysMacAddress.
            A value of 'true' indicates that CDP is enabled in
            this interface.
            A value of 'false' indicates that CDP is disabled in
            this interface."
       DEFVAL  { true }
       ::= { cLApEthernetIfEntry 33 }

cLApEthernetIfMtu OBJECT-TYPE
        SYNTAX     Unsigned32
        MAX-ACCESS read-only
        STATUS     current
        DESCRIPTION
                "This object represents interface's MTU value"
        ::= { cLApEthernetIfEntry 34 }

cLApEthernetIfType OBJECT-TYPE
       SYNTAX      IANAifType
       MAX-ACCESS  read-only
       STATUS      current
       DESCRIPTION
               "The type of interface.  Additional values for ifType
               are assigned by the Internet Assigned Numbers
               Authority (IANA), through updating the syntax of the
               IANAifType textual convention."
       ::= { cLApEthernetIfEntry 35 }
                                                             
cLApEthernetIfLinkChangeCount OBJECT-TYPE
        SYNTAX      Counter32
        MAX-ACCESS  read-only
        STATUS      current
        DESCRIPTION
                "This object represents the link change count of
                 ethernet interface on the AP."
        ::= { cLApEthernetIfEntry 36 }
                                                             
--********************************************************************
-- *  AP Dot11 radio Information
--********************************************************************
cLApDot11RadioTable OBJECT-TYPE
        SYNTAX SEQUENCE OF CLApDot11RadioEntry
        MAX-ACCESS not-accessible
        STATUS     current
        DESCRIPTION
                "This table represents the information about the
                basic functional parameters of the radios of the 
                APs that have joined the controller. "
        ::= { ciscoLwappApIf 3 }

cLApDot11RadioEntry OBJECT-TYPE
        SYNTAX     CLApDot11RadioEntry
        MAX-ACCESS not-accessible
        STATUS     current
        DESCRIPTION
                "An entry in this table represents the 802.11
                functional parameters of the radio of
                an AP that has joined the controller.

                Entries are added when the APs associate to this
                controller and deleted when they lose their
                association. " 
    INDEX           {
                        cLApSysMacAddress,
                        cLApDot11IfSlotId
                    } 
        ::= { cLApDot11RadioTable 1 }

CLApDot11RadioEntry ::= SEQUENCE {
        cLApDot11RadioMACAddress        MacAddress,
        cLApDot11RadioSubBand           CLApDot11RadioSubband,
        cLApDot11RadioVersion           DisplayString,
        cLApDot11IsBackhaul             TruthValue,
        cLApDot11RadioRole              CLApDot11RadioRole,
        cLApDot11RadioMode       INTEGER,
        cLApDot11RadioSubType    INTEGER
-- place holders for future variables
--> cLApDot11RadioChannelBandwidth
--> cLApDot11RadioChannelNumber
--> Channel assignment method
--> channel list - now in bsnwras MIB
--> isBackhaul
--> 
        }

cLApDot11RadioMACAddress OBJECT-TYPE
        SYNTAX     MacAddress
        MAX-ACCESS read-only
        STATUS     current
        DESCRIPTION
                "This object represents the base Mac address of
                 the radio."
        ::= { cLApDot11RadioEntry 1 }

cLApDot11RadioSubBand   OBJECT-TYPE
        SYNTAX     CLApDot11RadioSubband
        MAX-ACCESS read-only
        STATUS     current
        DESCRIPTION
                "This object indicates the sub band on which
        this radio operates." 
        ::= { cLApDot11RadioEntry 2 }

cLApDot11RadioVersion OBJECT-TYPE
        SYNTAX     DisplayString (SIZE(1..50))
        MAX-ACCESS read-only
        STATUS     current
        DESCRIPTION
        "This attribute identifies firmware version
        of the radio." 
        ::= { cLApDot11RadioEntry 3 }

cLApDot11IsBackhaul OBJECT-TYPE
        SYNTAX     TruthValue
        MAX-ACCESS read-only
        STATUS     current
        DESCRIPTION
                "This object represents whether this interface 
		is backhaul radio or not."
        ::= { cLApDot11RadioEntry 4 } 

cLApDot11RadioRole OBJECT-TYPE
        SYNTAX     CLApDot11RadioRole
        MAX-ACCESS read-only
        STATUS     current
        DESCRIPTION
                "This attribute identifies role of the radio."
        ::= { cLApDot11RadioEntry 5 }

cLApDot11RadioMode OBJECT-TYPE
    SYNTAX          INTEGER  {
                        local(1),
                        monitor(2),
                        remote(3),
                        rogueDetector(4),
                        sniffer(5),
                        bridge(6),
                        seConnect(7),
                        hybridRemote(8)
                    }
    MAX-ACCESS      read-only
    STATUS          current
    DESCRIPTION
        "This object indicates mode of the radio.
        local(1)         : The default option. Serving WLAN  
                           clients and scanning channels for threats. 
        monitor(2)       : A monitor mode.  AP spends all of its 
                           cycles scanning channels and looking 
                           for rogues. 
        remote(3)        : This mode indicates that AP is a remote 
                           edge lightweight access point. 
        rogueDetector(4) : This mode monitors the rogue APs on wire. 
                           It does not transmit or receive frames 
                           over the air or contain rogue APs. 
        sniffer(5)       : The access point starts sniffing 
                           the air on a given channel. 
        bridge(6)        : This mode indicates that a root AP 
                           is connected.
        seConnect(7)     : AP is connected to spectrum expert. 
                           The AP is able to perform spectrum 
                           intelligence.  
        hybridRemote(8)  : A mode for branch office and 
                           remote office deployment." 
    ::= { cLApDot11RadioEntry 6 }

cLApDot11RadioSubType OBJECT-TYPE
    SYNTAX          INTEGER  {
                        main(1),
                        rxOnly(2),
                        slaveAc(3),
                        remoteLan(4),
                        xorTxRx(5)
                    }
    MAX-ACCESS      read-only
    STATUS          current
    DESCRIPTION
        "This object indicates subtype of the radio.
        main(1)   :radio operates normally. 
        rxOnly(2) :NOS radio type,which is explicitely used 
                   for monitor mode operation.
        slaveAc(3):x-ale radio type is only for local mode." 
    ::= { cLApDot11RadioEntry 7 }
 



--********************************************************************
-- *  Global AP Credentials 
--********************************************************************

cLApCredentialGlobalUserName OBJECT-TYPE
       SYNTAX     SnmpAdminString
       MAX-ACCESS read-write
       STATUS     current
       DESCRIPTION
             "This object represents the global username for
             all the APs already joined or will join the controller.
             This user name is used to access the console on the AP." 
        ::= { ciscoLwappApCredentials  1 } 

cLApCredentialGlobalPassword OBJECT-TYPE
        SYNTAX     SnmpAdminString
        MAX-ACCESS read-write
        STATUS     current
        DESCRIPTION
             "This object represents the password corresponding to 
             the user name represented by cLApCredentialGlobalUserName
             object."
        ::= { ciscoLwappApCredentials  2 } 

cLApCredentialGlobalSecret OBJECT-TYPE 
        SYNTAX     SnmpAdminString
        MAX-ACCESS read-write
        STATUS     current
        DESCRIPTION
             "This object represents the secret key for
             all the APs already joined or will join the 
             controller. This provides read-write access 
             to the console on the AP." 
        ::= { ciscoLwappApCredentials  3 } 
	
--********************************************************************
-- * Per AP Credentials 
--********************************************************************

cLApCredentialsTable OBJECT-TYPE
        SYNTAX     SEQUENCE OF  CLApCredentialsEntry
        MAX-ACCESS not-accessible
        STATUS     current
        DESCRIPTION
             "This table provides the information about the credentials 
             of the 802.11 LWAPP Access Points that have joined the 
             controller. Rows are added to this table whenever, new APs 
             are joined to this controller, and rows are deleted 
             whenever APs gets disjoined from the controller."
        ::= { ciscoLwappApCredentials  4 }

cLApCredentialsEntry   OBJECT-TYPE
        SYNTAX     CLApCredentialsEntry
        MAX-ACCESS not-accessible
        STATUS     current
        DESCRIPTION
             "Each entry in this table provides information about
             one 802.11 LWAPP Access Point that has joined the
             controller. cLApSysMacAddress is the index which
             uniquely identifies every row in the table."
        INDEX   { cLApSysMacAddress }
        ::= { cLApCredentialsTable 1 }

CLApCredentialsEntry ::= SEQUENCE {
                cLApCredentialUserName                  SnmpAdminString,
                cLApCredentialPassword                  SnmpAdminString,
                cLApCredentialSecret                    SnmpAdminString,
                cLApCredentialEnableGlobalCredentials   TruthValue
        }

cLApCredentialUserName      OBJECT-TYPE
        SYNTAX     SnmpAdminString
        MAX-ACCESS  read-create
        STATUS     current
        DESCRIPTION
               "This object represents the username for
               this AP." 
        ::= { cLApCredentialsEntry   1 } 

cLApCredentialPassword      OBJECT-TYPE
        SYNTAX     SnmpAdminString
        MAX-ACCESS read-create
        STATUS     current
        DESCRIPTION
             "This object represents the password corresponding to 
             user name represented by cLApCredentialUserName object."
        ::= { cLApCredentialsEntry   2 } 

cLApCredentialSecret      OBJECT-TYPE
        SYNTAX     SnmpAdminString
        MAX-ACCESS read-create
        STATUS     current
        DESCRIPTION
             "This object represents the secret key for
             the specific AP. This provides the read-write access
             on the console for this AP." 
        ::= { cLApCredentialsEntry   3 } 

cLApCredentialEnableGlobalCredentials  OBJECT-TYPE
        SYNTAX     TruthValue
        MAX-ACCESS read-create
        STATUS     current
        DESCRIPTION
             "This object  specifies whether the global credentials
             for the AP is enabled or disabled.

             A value of 'true' enables the global username/password
             to be used for this AP and 'false' disables the global
             credentials and uses the credentials specific for this
             AP." 
        ::= { cLApCredentialsEntry   4 } 

--********************************************************************
-- *  Link Latency parameters
--********************************************************************
cLApLinkLatencyTable OBJECT-TYPE
        SYNTAX     SEQUENCE OF CLApLinkLatencyEntry
        MAX-ACCESS not-accessible
        STATUS     current
        DESCRIPTION
                "This table represents the link latency configuration 
                for each AP. 
                An entry is automatically added to this table when 
                an Access Points Joins controller. 
                Entry is removed from this table when AP 
                disassociates from the controllers."
        ::= { ciscoLwappLinkLatency 1 }


cLApLinkLatencyEntry OBJECT-TYPE
        SYNTAX     CLApLinkLatencyEntry
        MAX-ACCESS not-accessible
        STATUS     current
        DESCRIPTION
                "Each entry in this table provides configuration 
                related to Link latency on each AP. "
        INDEX   { cLApSysMacAddress }
        ::= { cLApLinkLatencyTable 1 }

CLApLinkLatencyEntry ::= SEQUENCE {
                cLApLinkLatencyEnable TruthValue,
        cLApLinkLatencyReset  TruthValue
        }

cLApLinkLatencyEnable OBJECT-TYPE
       SYNTAX      TruthValue
       MAX-ACCESS  read-write
       STATUS      current
       DESCRIPTION
               "This object can be used to configure the Link 
               Latency on the AP.             
               A value of 'true' indicates that the Link Latency
               is enabled.
               A value of 'false' indicates that the Link Latency 
               is disabled."
       DEFVAL { false }
        ::= {  cLApLinkLatencyEntry 1 }

cLApLinkLatencyReset OBJECT-TYPE
       SYNTAX      TruthValue
       MAX-ACCESS  read-write
       STATUS      current
       DESCRIPTION
               "This object can be used to reset the Link Latency 
               stored at controller for an AP.             
               A value of true indicates that the Link Latency stats 
               is to be reset.
               A value of false on this during set will return error.
               A value of false will be returned on get."    
       DEFVAL { false }   
        ::= {  cLApLinkLatencyEntry 2 }

--********************************************************************
-- *  Link Latency Stats
--********************************************************************

cLApLinkLatencyStatsTable OBJECT-TYPE
        SYNTAX     SEQUENCE OF CLApLinkLatencyStatsEntry
        MAX-ACCESS not-accessible
        STATUS     current
        DESCRIPTION
                "This table represents the link latency statistics 
                calculated for each AP. 
                An entry is automatically added by the controller
                when a 'cLApLinkLatencyEnable' is enabled on an 
                Access Point. Entry is deleted when 
                'cLApLinkLatencyEnable' is disabled on the 
                Access Point."
        ::= { ciscoLwappLinkLatency 2 }


cLApLinkLatencyStatsEntry OBJECT-TYPE
        SYNTAX     CLApLinkLatencyStatsEntry
        MAX-ACCESS not-accessible
        STATUS     current
        DESCRIPTION
        "Each entry in this table provides minimum, maximum
        and average Link latency for a Access Point. 
        Entries are removed when the Link Latency is disabled 
        on a Access Point."
        INDEX   { cLApSysMacAddress }
        ::= { cLApLinkLatencyStatsTable 1 }

CLApLinkLatencyStatsEntry ::= SEQUENCE {
                cLApLinkLatencyStatsCurrent TimeInterval,
                cLApLinkLatencyStatsMin TimeInterval,
                cLApLinkLatencyStatsMax TimeInterval,
                cLApLinkLatencyTimeStamp TimeStamp,
                cLApDataLinkLatencyStatsCurrent TimeInterval,
                cLApDataLinkLatencyStatsMin TimeInterval,
                cLApDataLinkLatencyStatsMax TimeInterval,
                cLApDataLinkLatencyTimeStamp TimeStamp
        }

cLApLinkLatencyStatsCurrent OBJECT-TYPE
       SYNTAX      TimeInterval
       UNITS           "milliseconds"
       MAX-ACCESS  read-only
       STATUS      current
       DESCRIPTION
        "This object represent the current Link latency recorded for
        this Access point." 
        ::= {  cLApLinkLatencyStatsEntry  1}

cLApLinkLatencyStatsMin OBJECT-TYPE
       SYNTAX      TimeInterval
       UNITS           "milliseconds"
       MAX-ACCESS  read-only
       STATUS      current
       DESCRIPTION
        "This object represent the minimum Link latency recorded for
        this Access point." 
        ::= {  cLApLinkLatencyStatsEntry  2}

cLApLinkLatencyStatsMax OBJECT-TYPE
       SYNTAX      TimeInterval
       UNITS           "milliseconds"
       MAX-ACCESS  read-only
       STATUS      current
       DESCRIPTION
        "This object represent the maximum Link latency recorded for
        this Access point." 
        ::= {  cLApLinkLatencyStatsEntry  3}

cLApLinkLatencyTimeStamp OBJECT-TYPE
       SYNTAX      TimeStamp
       UNITS       "seconds"
       MAX-ACCESS  read-only
       STATUS      current
       DESCRIPTION
        "This object represents the timestamp, when the values are
        collected, as returned by the object 'cLApUpTime'." 
        ::= {  cLApLinkLatencyStatsEntry  4}
        
cLApDataLinkLatencyStatsCurrent OBJECT-TYPE
       SYNTAX      TimeInterval
       UNITS           "milliseconds"
       MAX-ACCESS  read-only
       STATUS      current
       DESCRIPTION
        "This object represent the current Data Link latency recorded
        for this Access point." 
        ::= {  cLApLinkLatencyStatsEntry  5}

cLApDataLinkLatencyStatsMin OBJECT-TYPE
       SYNTAX      TimeInterval
       UNITS           "milliseconds"
       MAX-ACCESS  read-only
       STATUS      current
       DESCRIPTION
        "This object represent the minimum Data Link latency recorded
        for this Access point." 
        ::= {  cLApLinkLatencyStatsEntry  6}

cLApDataLinkLatencyStatsMax OBJECT-TYPE
       SYNTAX      TimeInterval
       UNITS           "milliseconds"
       MAX-ACCESS  read-only
       STATUS      current
       DESCRIPTION
        "This object represent the maximum Data Link latency recorded
        for this Access point." 
        ::= {  cLApLinkLatencyStatsEntry  7}

cLApDataLinkLatencyTimeStamp OBJECT-TYPE
       SYNTAX      TimeStamp
       UNITS       "seconds"
       MAX-ACCESS  read-only
       STATUS      current
       DESCRIPTION
        "This object represents the timestamp, when the values are
        collected, as returned by the object 'cLApUpTime'." 
        ::= {  cLApLinkLatencyStatsEntry  8}

--********************************************************************
-- *  AP LAN Stats.
--********************************************************************

cLAplanStatsTable OBJECT-TYPE
       SYNTAX     SEQUENCE OF CLAplanStatsEntry
       MAX-ACCESS not-accessible
       STATUS     current
       DESCRIPTION
               "This table represents Saridinia AP LAN stats
                information that have joined the controller."
        ::= { ciscoLwappAplanStats 1 }

cLAplanStatsEntry OBJECT-TYPE
       SYNTAX     CLAplanStatsEntry
       MAX-ACCESS not-accessible
       STATUS     current
       DESCRIPTION
               "This entry contains stats information of
                LAN stats"
       INDEX   {
                cLApSysMacAddress,
                cLApLanPortId
               }
        ::= { cLAplanStatsTable 1 }

CLAplanStatsEntry ::= SEQUENCE {
		cLApLanPortId                   INTEGER,
		cLApLanPortState                TruthValue,
		cLApLanPortVlanId		Unsigned32,
		cLApLanPortVlanIdValid          TruthValue,
		cLApLanPoeState			TruthValue
        }

cLApLanPortId OBJECT-TYPE
       SYNTAX     INTEGER (1..4)
       MAX-ACCESS not-accessible
       STATUS     current
       DESCRIPTION
               "This object represents the ID of a LAN
               Port on Sardinia AP."
        ::= {  cLAplanStatsEntry 1 }
		
cLApLanPortState OBJECT-TYPE
       SYNTAX     TruthValue
       MAX-ACCESS read-write
       STATUS     current
       DESCRIPTION
               "This object represents the LAN port ID Stats  of an
                Ethernet interface on  Sardinia AP."
       DEFVAL  { false }
        ::= {  cLAplanStatsEntry  2 }

cLApLanPortVlanId OBJECT-TYPE
       SYNTAX     Unsigned32 (0..4094)
       MAX-ACCESS read-write
       STATUS     current
       DESCRIPTION
                "This object represents the VlanID Range(2-4094) 
		 and VlanId =0 to disable vlan access of a VLAN
		 LAN Port on Sardinia AP."
       DEFVAL  { 0 }
        ::= {  cLAplanStatsEntry 3 }

cLApLanPortVlanIdValid  OBJECT-TYPE
       SYNTAX     TruthValue
       MAX-ACCESS read-only
       STATUS     current
       DESCRIPTION
               "This object represents VLAN ID is valid for LAN
		Port interface on Sardinia AP."
       DEFVAL  { false }
        ::= {  cLAplanStatsEntry  4 }

cLApLanPoeState OBJECT-TYPE
       SYNTAX     TruthValue
       MAX-ACCESS read-write
       STATUS     current
       DESCRIPTION
               "This object represents the LAN Poe Status  of an
                Ethernet interface on AP"
       DEFVAL  { false }
        ::= {  cLAplanStatsEntry  5 }

cLAplanOverrideTable OBJECT-TYPE
       SYNTAX     SEQUENCE OF CLAplanOverrideEntry
       MAX-ACCESS not-accessible
       STATUS     current
       DESCRIPTION
               "This table represents the lan override status of AP"
        ::= { ciscoLwappAplanStats 2 }

cLAplanOverrideEntry OBJECT-TYPE
       SYNTAX     CLAplanOverrideEntry
       MAX-ACCESS not-accessible
       STATUS     current
       DESCRIPTION
               "This entry contains stats information of LAN override status"
       INDEX   {
                cLApSysMacAddress
               }
        ::= { cLAplanOverrideTable 1 }

CLAplanOverrideEntry ::= SEQUENCE {
		cLApLanOverride    TruthValue
        }

cLApLanOverride OBJECT-TYPE
       SYNTAX     TruthValue
       MAX-ACCESS read-write
       STATUS     current
       DESCRIPTION
               "This object represents the LAN port override status of AP"
       DEFVAL  { false }
        ::= {  cLAplanOverrideEntry  1 }


--********************************************************************
-- *  AP WLAN Stats.
--********************************************************************

cLApWlanStatsTable OBJECT-TYPE
        SYNTAX     SEQUENCE OF CLApWlanStatsEntry
        MAX-ACCESS not-accessible
        STATUS     current
        DESCRIPTION
                "This table represents Per-AP, Per-Radio, Per-SSID 
                Stats information of packets/bytes sent/received,
                retransmission counter, associated clients counter,
                etc."
        ::= { ciscoLwappApWlanStats 1 }

cLApWlanStatsEntry OBJECT-TYPE
        SYNTAX     CLApWlanStatsEntry
        MAX-ACCESS not-accessible
        STATUS     current
        DESCRIPTION
                "This entry contains stats information of
                 packets/bytes sent/received, retransmission counter,
                 associated clients counter, and etc."
        INDEX   {
                    cLApSysMacAddress,
                    cLApDot11IfType,
                    cLWlanIndex
                }
        ::= { cLApWlanStatsTable 1 }

CLApWlanStatsEntry ::= SEQUENCE {
                cLApWlanStatsTxPktNum           Counter64,
                cLApWlanStatsTxOctetNum         Counter64,
                cLApWlanStatsRxPktNum           Counter64,
                cLApWlanStatsRxOctetNum         Counter64,
                cLApWlanStatsRetransmitNum      Counter64,
                cLApWlanStatsAssocClientNum     Unsigned32,
                cLApWlanStatsOnlineUserNum      Unsigned32
        }

cLApWlanStatsTxPktNum OBJECT-TYPE
       SYNTAX      Counter64
       MAX-ACCESS  read-only
       STATUS      current
       DESCRIPTION
        "This object represents the transmitted packets counter of
        the specific radio and wlan on this access point." 
        ::= { cLApWlanStatsEntry  1 }

cLApWlanStatsTxOctetNum OBJECT-TYPE
       SYNTAX      Counter64
       MAX-ACCESS  read-only
       STATUS      current
       DESCRIPTION
        "This object represents the transmitted bytes counter of
        the specific radio and wlan on this access point." 
        ::= { cLApWlanStatsEntry  2 }

cLApWlanStatsRxPktNum OBJECT-TYPE
       SYNTAX      Counter64
       MAX-ACCESS  read-only
       STATUS      current
       DESCRIPTION
        "This object represents the received packets counter of
        the specific radio and wlan on this access point." 
        ::= { cLApWlanStatsEntry  3 }

cLApWlanStatsRxOctetNum OBJECT-TYPE
       SYNTAX      Counter64
       MAX-ACCESS  read-only
       STATUS      current
       DESCRIPTION
        "This object represents the received bytes counter of
        the specific radio and wlan on this access point." 
        ::= { cLApWlanStatsEntry  4 }

cLApWlanStatsRetransmitNum OBJECT-TYPE
       SYNTAX      Counter64
       MAX-ACCESS  read-only
       STATUS      current
       DESCRIPTION
        "This object represents the packet retransmission counter of
        the specific radio and wlan on this access point." 
        ::= { cLApWlanStatsEntry  5 }

cLApWlanStatsAssocClientNum OBJECT-TYPE
       SYNTAX      Unsigned32
       MAX-ACCESS  read-only
       STATUS      current
       DESCRIPTION
        "This object represents the associated client counter of
        the specific radio and wlan on this access point." 
        ::= { cLApWlanStatsEntry  6 }

cLApWlanStatsOnlineUserNum OBJECT-TYPE
       SYNTAX      Unsigned32
       MAX-ACCESS  read-only
       STATUS      current
       DESCRIPTION
        "This object represents the online user counter of
        the specific radio and wlan on this access point."
        ::= { cLApWlanStatsEntry  7 }

--********************************************************************
-- *  AP Station Mgmt(SMT) Parameters
--********************************************************************

cLApIfSmtParamTable OBJECT-TYPE
        SYNTAX SEQUENCE OF CLApIfSmtParamEntry
        MAX-ACCESS not-accessible
        STATUS     current
        DESCRIPTION
                "This table represents the station management
                information in the APs that have joined the
                controller.  Information populated through the
                entries of this table is used by the AP to
                perform the expected 802.11 operations on
                the respective dot11 interfaces to coordinate with
                other 802.11 devices in the network.

                Since this table has the indices defined in the
                tables cLApTable and cLApDot11IfTable, an entry in
                this table is automatically removed when the
                respective entry is removed in either of those
                tables. "  
        ::= { ciscoLwappAp 2 }

cLApIfSmtParamEntry OBJECT-TYPE
        SYNTAX     CLApIfSmtParamEntry
        MAX-ACCESS not-accessible
        STATUS     current
        DESCRIPTION
                "An entry in this table represents the information
                pertaining to one particular dot11 interface of
                this AP used to perform the 802.11 protocol
                operations on the respective dot11 interface.
 
                Rows are added or deleted to this table when
                APs join or leave the controller respectively. "
    INDEX           {
                        cLApSysMacAddress,
                        cLApDot11IfSlotId
                    } 
    ::= { cLApIfSmtParamTable 1 }

CLApIfSmtParamEntry ::= SEQUENCE {
                cLApIfSmtDot11Bssid MacAddress
        }

cLApIfSmtDot11Bssid OBJECT-TYPE
        SYNTAX     MacAddress
        MAX-ACCESS read-only
        STATUS     current
        DESCRIPTION
                "This object defines the base BSSID of this AP, which
                is the MAC address of the radio interface of this
                AP. "
    ::= { cLApIfSmtParamEntry 1 }


-- ********************************************************************
-- Country code setting for APs that have joined the controller
-- ********************************************************************

cLApCountryTable OBJECT-TYPE
        SYNTAX     SEQUENCE OF CLApCountryEntry
        MAX-ACCESS not-accessible
        STATUS     current
        DESCRIPTION
                "This table represents the country settings for
                the 802.11 LWAPP Access Points that have joined the
                controller.
                An entry is automatically added by the controller 
                when a Access Point joins the controller. 
                The entry is removed when Access Point disasscociates 
                from the controller."
        ::= { ciscoLwappAp 3 }


cLApCountryEntry OBJECT-TYPE
        SYNTAX     CLApCountryEntry
        MAX-ACCESS not-accessible
        STATUS     current
        DESCRIPTION
                "Each entry in this table provides country setting
                about one 802.11 LWAPP Access Point that has joined 
                the controller.
                Entries are removed when the APs lose their
                association with the controller due to loss
                of communication."
        INDEX   { cLApSysMacAddress }
        ::= { cLApCountryTable 1 }

CLApCountryEntry ::= SEQUENCE {
                cLApCountryCode     DisplayString,
                cLApCountryAllowed  DisplayString
        }

cLApCountryCode OBJECT-TYPE
        SYNTAX DisplayString (SIZE(1..255))
        MAX-ACCESS read-write
        STATUS     current
        DESCRIPTION
                "This attribute identifies the country in which the
                AP is operating. This value is the 3 letter country  
                code."
        ::= { cLApCountryEntry 1 }

cLApCountryAllowed OBJECT-TYPE
        SYNTAX DisplayString (SIZE(1..255))
        MAX-ACCESS read-only
        STATUS     current
        DESCRIPTION
                "This attribute identifies the country in which the
                AP is operating. This value is a list of country  
                codes sperated by comma."
        ::= { cLApCountryEntry 2 }


--*****************************************************************************
--* Halo BLE Configuration to set Beacon parameters of Halo enabled APs 
--*****************************************************************************
cLHaloGlobalBleBeaconInterval OBJECT-TYPE
       SYNTAX      Unsigned32 (1..10)
       UNITS       "Hz"
       MAX-ACCESS  read-write
       STATUS      current
       DESCRIPTION
                "This object represent the beacon interval
                between each transmissions from BLE module.
                This value is common to HALO enabled APs that
                have joined the controller."
       DEFVAL  { 1 }
        ::= { ciscoLwappApGlobalBleBeacon 1}

cLHaloBleBeaconTable OBJECT-TYPE
       SYNTAX     SEQUENCE OF CLHaloBleBeaconEntry
       MAX-ACCESS not-accessible
       STATUS     current
       DESCRIPTION
               "This table represents BLE global configuration.It lists
		the ibeacon's identification number and attenuation value
		which is common to HALO enabled AP's that 
		have joined the controller."
        ::= { ciscoLwappApGlobalBleBeacon  2 }

cLHaloBleBeaconEntry OBJECT-TYPE
       SYNTAX     CLHaloBleBeaconEntry
       MAX-ACCESS not-accessible
       STATUS     current
       DESCRIPTION
               "This entry contains BLE global configuration which lists
		the ibeacon's identification number and attenuation value
		of HALO enabled APs that have joined the controller."
       INDEX   {
               cLHaloGlobalBleBeaconId
               }
        ::= { cLHaloBleBeaconTable 1 }

CLHaloBleBeaconEntry ::= SEQUENCE {
                cLHaloGlobalBleBeaconId           Unsigned32,
                cLHaloGlobalBleBeaconUuid         DisplayString,
                cLHaloGlobalBleBeaconTxPower      Unsigned32,
                cLHaloGlobalBleBeaconEnable       TruthValue
                }

cLHaloGlobalBleBeaconId OBJECT-TYPE
       SYNTAX     Unsigned32
       MAX-ACCESS not-accessible
       STATUS     current
       DESCRIPTION
               "This object represents BLE ibeacon ID for 
		which gloabl BLE configurations to be 
		applied."
        ::= { cLHaloBleBeaconEntry 1 }



cLHaloGlobalBleBeaconUuid OBJECT-TYPE
       SYNTAX DisplayString (SIZE(0..128))
       MAX-ACCESS read-write
       STATUS     current
       DESCRIPTION
               "This object represents the UUID (universally unique identifier)
                which is a 128-bit value."
        ::= { cLHaloBleBeaconEntry 2 }


cLHaloGlobalBleBeaconTxPower  OBJECT-TYPE
       SYNTAX     Unsigned32 (0..52)
       UNITS      "dBm"
       MAX-ACCESS read-write
       STATUS     current
       DESCRIPTION
               "This object represents TX power of particular ibeacon for 
		HALO enabled APs that have joined the controller.The TX power
		is based on size of proximity zone needed."
        ::= { cLHaloBleBeaconEntry 3}


cLHaloGlobalBleBeaconEnable  OBJECT-TYPE
       SYNTAX      TruthValue
       MAX-ACCESS  read-write
       STATUS      current
       DESCRIPTION
              "This object specifies the status of the BLE beacons.
               enable(1) - enable the BLE beacon,
               disable(2) - disable the BLE beacon."
        ::= { cLHaloBleBeaconEntry 4}


cLApBleBeaconTable OBJECT-TYPE
       SYNTAX     SEQUENCE OF CLApBleBeaconEntry
       MAX-ACCESS not-accessible
       STATUS     current
       DESCRIPTION
               "This table represents BLE ibeacon's AP specific configuration 
		for HALO enabled APs that have joined the controller."
        ::= { ciscoLwappApGlobalBleBeacon 3 }

cLApBleBeaconEntry OBJECT-TYPE
       SYNTAX     CLApBleBeaconEntry
       MAX-ACCESS not-accessible
       STATUS     current
       DESCRIPTION
               "This entry contains BLE Beacon's AP specific configuration." 
       INDEX   {
               cLApSysMacAddress,
               cLHaloGlobalBleBeaconId 
               }
        ::= { cLApBleBeaconTable 1 }

CLApBleBeaconEntry ::= SEQUENCE {
                cLApBleBeaconMajorField           Unsigned32,
                cLApBleBeaconMinorField           Unsigned32,
                cLApBleBeaconTxPower              Unsigned32,
                cLApBleBeaconStatus               TruthValue,
                cLApBleBeaconUuid                 DisplayString,
                cLApBleBeaconInterval             Unsigned32,
                cLApBleBeaconApplyGlobal          TruthValue
                }

cLApBleBeaconMajorField OBJECT-TYPE
       SYNTAX     Unsigned32
       MAX-ACCESS read-write
       STATUS     current
       DESCRIPTION
               "This object represents the Major value of ibeacon
		that is used to differentiate ibeacons that have the same
		proximity UUID."
        ::= {  cLApBleBeaconEntry  1 }

cLApBleBeaconMinorField OBJECT-TYPE
       SYNTAX     Unsigned32
       MAX-ACCESS read-write
       STATUS     current
       DESCRIPTION
                "This object represents the Minor value of ibeacon
		 that is used to differentiate ibeacons that have the same
		 proximity UUID and has same major value."
        ::= {  cLApBleBeaconEntry 2 }

cLApBleBeaconTxPower  OBJECT-TYPE
       SYNTAX     Unsigned32 (0..52)
       UNITS      "dBm"
       MAX-ACCESS read-write
       STATUS     current
       DESCRIPTION
               "This object represents TX power of particular ibeacon for 
		specified HALO enabled AP. The TX power value is based on 
		the size of proximity zone needed."
        ::= {  cLApBleBeaconEntry  3 }

cLApBleBeaconStatus OBJECT-TYPE
       SYNTAX      TruthValue
       MAX-ACCESS  read-write
       STATUS      current
       DESCRIPTION 
              "This object specifies the status of the BLE beacons.
               enable(1) - enable the BLE beacon,
               disable(2) - disable the BLE beacon."
        ::= {  cLApBleBeaconEntry 4 }
	
cLApBleBeaconUuid OBJECT-TYPE
       SYNTAX     DisplayString (SIZE(0..128))
       MAX-ACCESS read-write
       STATUS     current
       DESCRIPTION
               "This object represents the UUID (universally unique identifier)
                which is a 128-bit value."
        ::= { cLApBleBeaconEntry 5 }

cLApBleBeaconInterval OBJECT-TYPE
       SYNTAX      Unsigned32 (1..10)
       UNITS       "Hz"
       MAX-ACCESS  read-write
       STATUS      current
       DESCRIPTION
                "This object represent the beacon interval
                between each transmissions from BLE module.
                This value is common to HALO enabled APs that
                have joined the controller."
       DEFVAL  { 1 }
        ::= { cLApBleBeaconEntry 6 }

cLApBleBeaconApplyGlobal OBJECT-TYPE
       SYNTAX      TruthValue
       MAX-ACCESS  read-write
       STATUS      current
       DESCRIPTION
              "Setting this to true will clear all BLE configuration at AP and 
               sets with Global BLE configuration when applied.
               Set 1(True), above action takes place.
               Set 2(False), no action takes place."
       DEFVAL { false }
       ::= { cLApBleBeaconEntry 7 }

--*****************************************************************************
--* Halo BLE Module Mibs
--*****************************************************************************

--********************************************************************
-- *  Notification Control Object 
--********************************************************************
ciscoLwappApIfRegulatoryDomainMismatchNotifEnabled OBJECT-TYPE
         SYNTAX     TruthValue
         MAX-ACCESS read-write
         STATUS     current
         DESCRIPTION
                 "The object to control the generation of
        ciscoLwappApIfRegulatoryDomainMismatchNotif 
        notification.

        A value of 'true' indicates that the agent 
        generates ciscoLwappApIfRegulatoryDomainMismatchNotif 
        notification.

                 A value of 'false' indicates that the agent doesn't
                 generate ciscoLwappApIfRegulatoryDomainMismatchNotif
                 notification."
         DEFVAL  { true }
         ::= { ciscoLwappAp 4 }

ciscoLwappApCrashEnabled OBJECT-TYPE
        SYNTAX     TruthValue
        MAX-ACCESS read-write
        STATUS     current
        DESCRIPTION
                "The object to control the generation of
                ciscoLwappApCrash notification.

                A value of 'true' indicates that the agent generates
                ciscoLwappApCrash notification.

                A value of 'false' indicates that the agent doesn't
                generate ciscoLwappApCrash notification."
        DEFVAL  { true }
        ::= { ciscoLwappAp 5 }

ciscoLwappApUnsupportedEnabled OBJECT-TYPE
        SYNTAX     TruthValue
        MAX-ACCESS read-write
        STATUS     current
        DESCRIPTION
                "The object to control the generation of
                ciscoLwappApUnsupported notification.

                A value of 'true' indicates that the agent generates
                ciscoLwappApUnsupported notification.

                A value of 'false' indicates that the agent doesn't
                generate ciscoLwappApUnsupported
                notification."
        DEFVAL  { true }
        ::= { ciscoLwappAp 6 }


ciscoLwappApAssociatedEnabled OBJECT-TYPE
        SYNTAX     TruthValue
        MAX-ACCESS read-write
        STATUS     current
        DESCRIPTION
                "The object to control the generation of
                ciscoLwappApAssociated notification.

                A value of 'true' indicates that the agent generates
                ciscoLwappApAssociated notification.

                A value of 'false' indicates that the agent doesn't
                generate ciscoLwappApAssociated notification."
        DEFVAL  { true }
        ::= { ciscoLwappAp 7 }
-- ********************************************************************
-- Spectrum Expert Connection parameters
-- ********************************************************************

cLApSeClientTable OBJECT-TYPE
        SYNTAX SEQUENCE OF CLApSeClientEntry 
        MAX-ACCESS not-accessible
        STATUS     current
        DESCRIPTION
        "This table represents the information about the
        details of Spectrum Expert client connected to 
        radio interface of APs"
        ::= { ciscoLwappApMIBObjects 8 }
 
cLApSeClientEntry OBJECT-TYPE
        SYNTAX     CLApSeClientEntry
        MAX-ACCESS not-accessible
        STATUS     current
        DESCRIPTION
        "An entry in this table represents the details of
        Spectrum Expert client connected to APs"
    INDEX           {
                        cLApSysMacAddress,
                        cLApDot11IfSlotId,
                        cLApSeIndex
                    } 
        ::= { cLApSeClientTable 1 }

CLApSeClientEntry ::= SEQUENCE {
        cLApSeIndex            Integer32,
        cLApSeClientUserName   SnmpAdminString,
        cLApSeClientIPAddrType InetAddressType,
        cLApSeClientIPAddr     InetAddress,
        cLApSeClientDuration   TimeInterval,
        cLApSeClientPort       InetPortNumber
        }

cLApSeIndex OBJECT-TYPE
       SYNTAX      Integer32
       MAX-ACCESS  not-accessible
       STATUS      current
       DESCRIPTION
        "This object indicates the index of the client
        running the Spectrum Expert instance." 
       ::= { cLApSeClientEntry 1 }

cLApSeClientUserName OBJECT-TYPE
	SYNTAX 	    SnmpAdminString
	MAX-ACCESS  read-only
	STATUS      current
	DESCRIPTION
        "This object indicates the name of the
        client running the Spectrum Expert application" 
	::= {cLApSeClientEntry 2}

cLApSeClientIPAddrType OBJECT-TYPE
       SYNTAX      InetAddressType
       MAX-ACCESS  read-only
       STATUS      current
       DESCRIPTION
        "This object indicates the client IP address type,
        that runs the SE application, made available 
        through cLApSeClientIPAddr" 
       ::= { cLApSeClientEntry 3 }

cLApSeClientIPAddr OBJECT-TYPE
       SYNTAX      InetAddress
       MAX-ACCESS  read-only
       STATUS      current
       DESCRIPTION
        "This object indicates the client IP address,
        that runs the SE application" 
       ::= { cLApSeClientEntry 4 }

cLApSeClientDuration OBJECT-TYPE
       SYNTAX      TimeInterval
       MAX-ACCESS  read-only
       STATUS      current
       DESCRIPTION
        "This object indicates the duration for which the SE client
        application has been up and running" 
	::= { cLApSeClientEntry 5}

cLApSeClientPort OBJECT-TYPE
       SYNTAX          InetPortNumber
       MAX-ACCESS  read-only
       STATUS      current
       DESCRIPTION
        "This object indicates the port from which the SE client
        application is running" 
	::= { cLApSeClientEntry 6}

-- ********************************************************************
-- Global settings for APs 
-- ********************************************************************
cLApFastHbTimerTable OBJECT-TYPE
        SYNTAX      SEQUENCE OF CLApFastHbTimerEntry
        MAX-ACCESS  not-accessible
        STATUS      current
        DESCRIPTION
          "This table contains entries for AP fast heartbeat
           timers configured in the controller. At startup,
           all the entries in this table are set up by the central
           controller.  A management application can later change
           the values in this table."
        ::= { ciscoLwappApGlobal 1 }

cLApFastHbTimerEntry OBJECT-TYPE
        SYNTAX      CLApFastHbTimerEntry
        MAX-ACCESS  not-accessible
        STATUS      current
        DESCRIPTION
          "A conceptual row in cLApFastHbTimerTable. There is an entry
           in this table for each AP type, as identified by a value of
           cLApFastHbTimerApType."
        INDEX   { cLApFastHbTimerApType }
        ::= { cLApFastHbTimerTable 1 }


CLApFastHbTimerEntry ::= SEQUENCE {
            cLApFastHbTimerApType        INTEGER,
            cLApFastHbTimerTimeout       Unsigned32,
            cLApFastHbTimerEnabled       TruthValue
        }

cLApFastHbTimerApType OBJECT-TYPE
      SYNTAX        INTEGER {
                                  local (1),
                                  hreap (2)
                            }
       MAX-ACCESS  not-accessible
       STATUS      current
       DESCRIPTION
           "This object represents the AP type for this entry.
                local      - indicates that timer is for local mode APs
        hreap      - indicates that timer is for HREAP APs" 
       ::= { cLApFastHbTimerEntry 1 }

cLApFastHbTimerTimeout OBJECT-TYPE
       SYNTAX      Unsigned32 (1..15)
       UNITS       "seconds"
       MAX-ACCESS  read-write
       STATUS      current
       DESCRIPTION
          "This object represents the timeout value for the heart
           beat timer. This value changes to 0 when
           cLApFastHbTimerEnabled is set to 'false'."
       ::= { cLApFastHbTimerEntry 2 }

cLApFastHbTimerEnabled OBJECT-TYPE
       SYNTAX      TruthValue
       MAX-ACCESS  read-write
       STATUS      current
       DESCRIPTION
          "This object controls the Heartbeat Timer. A value of 'true'
           indicates that this timer is enabled. A value of 'false'
           indicates that this timer is disabled."
       ::= { cLApFastHbTimerEntry 3 }

cLApPrimaryDiscoveryTimeout OBJECT-TYPE
       SYNTAX      Unsigned32 (30..3600)
       UNITS       "seconds"
       MAX-ACCESS  read-write
       STATUS      current
       DESCRIPTION
          "This object represents the timeout for the primary AP
           discovery."
        DEFVAL { 120 }
        ::= { ciscoLwappApGlobal 3 }

cLApGlobalPrimaryControllerAddressType OBJECT-TYPE
       SYNTAX      InetAddressType 
       MAX-ACCESS  read-write
       STATUS      current
       DESCRIPTION
          "This object represents the type of the primary controller's 
           address made available through cLApPrimaryControllerAddress."
        ::= { ciscoLwappApGlobal 4 }

cLApGlobalPrimaryControllerAddress OBJECT-TYPE
       SYNTAX      InetAddress
       MAX-ACCESS  read-write
       STATUS      current
       DESCRIPTION
          "This object represents the address of the primary controller
        that the APs will join. The name and address should be 
        provided in the same set request. An address of all zeros 
        will unset the primary controller." 
        ::= { ciscoLwappApGlobal 5 }

cLApGlobalPrimaryControllerName OBJECT-TYPE
       SYNTAX      SnmpAdminString (SIZE(0..32))
       MAX-ACCESS  read-write
       STATUS      current
       DESCRIPTION
          "This object represents the name of the primary controller
           that the APs will join."
        ::= { ciscoLwappApGlobal 6 }


cLApGlobalSecondaryControllerAddressType OBJECT-TYPE
       SYNTAX      InetAddressType 
       MAX-ACCESS  read-write
       STATUS      current
       DESCRIPTION
        "This object represents the type of the secondary
        controller's address made available through 
        cLApSecondaryControllerAddress." 
        ::= { ciscoLwappApGlobal 7 }

cLApGlobalSecondaryControllerAddress OBJECT-TYPE
       SYNTAX      InetAddress
       MAX-ACCESS  read-write
       STATUS      current
       DESCRIPTION
        "This object represents the address of the secondary
        controller that the APs will join. The name and address 
        should be provided in the same set request. An address 
        of all zeros will unset the secondary controller." 
        ::= { ciscoLwappApGlobal 8 }

cLApGlobalSecondaryControllerName OBJECT-TYPE
       SYNTAX      SnmpAdminString (SIZE(0..32))
       MAX-ACCESS  read-write
       STATUS      current
       DESCRIPTION
          "This object represents the name of the secondary controller
           that the APs will join."
        ::= { ciscoLwappApGlobal 9 }

cLApGlobalFailoverPriority OBJECT-TYPE
       SYNTAX      TruthValue
       MAX-ACCESS  read-write
       STATUS      current
       DESCRIPTION
          "This object represents the Global AP Failover priority. 
        If Enabled, Priorities will be considered of the APs which 
        wishes to join the controller. Preference will be given to 
        the higher priority AP. If the number of associated AP has 
        already reached the limit then the controller will 
        disassociate a lower priority AP to accomodate a higher 
        priority AP. 
	       Default is Disabled state."
       DEFVAL {false}
        ::= { ciscoLwappApGlobal 10 }

cLApGlobalTcpMss OBJECT-TYPE
		SYNTAX	INTEGER (0 | 536..1363)
		MAX-ACCESS	read-write
		STATUS		current
		DESCRIPTION
			"This object represents the Global AP TCP MSS value.
			Permissible value are between 536 and 1363. This will
			also enable the global TCP MSS flag.
			Value of 0 will disable the global TCP MSS flag.
			Any change of value for this object will be reflected
			to cLApTcpMss"
		::= { ciscoLwappApGlobal 11 }

cLApGlobalDot11IfTable OBJECT-TYPE
        SYNTAX SEQUENCE OF CLApGlobalDot11IfEntry
        MAX-ACCESS not-accessible
        STATUS     current
        DESCRIPTION
        "This table is used to configure the global dot11
        parameters per slot id, represented by cLApDot11IfSlotId, 
        of the radio interface in all the APs joined with 
        the controller."
        ::= { ciscoLwappApGlobal 12 }


cLApGlobalDot11IfEntry OBJECT-TYPE
        SYNTAX     CLApGlobalDot11IfEntry
        MAX-ACCESS not-accessible
        STATUS     current
        DESCRIPTION
        "This represents an entry in the
        cLApGlobalDot11IfTable."
        INDEX { cLApDot11IfSlotId }
        ::= { cLApGlobalDot11IfTable 1 }

CLApGlobalDot11IfEntry ::= SEQUENCE {
                cLApGlobalDot11IfCdpEnabled      TruthValue
        }

cLApGlobalDot11IfCdpEnabled   OBJECT-TYPE
       SYNTAX      TruthValue
       MAX-ACCESS  read-write
       STATUS      current
       DESCRIPTION
            "This object is used to configure the Cisco Discovery
            Protocol(CDP) in the interface, represented by
        cLApDot11IfSlotId of the all the APs, joined in the 
        controller.

        Setting this object to a value of 'true' would turn on 
        the CDP on this slot.

            Setting this object to a value of 'false' would turn off the
            CDP on this slot, so that CDP advertisements are not sent.

        Read operation on this attribute will not be supported. 
        When queried this will return a value of 'false'." 
       ::= { cLApGlobalDot11IfEntry 1 }

cLApGlobalEthernetIfTable OBJECT-TYPE
        SYNTAX SEQUENCE OF CLApGlobalEthernetIfEntry
        MAX-ACCESS not-accessible
        STATUS     current
        DESCRIPTION
        "This table is used to configure the global parameters
        on Ethernet interfaces of all the APs joined with the 
        controller."
        ::= { ciscoLwappApGlobal 13 }

cLApGlobalEthernetIfEntry OBJECT-TYPE
        SYNTAX     CLApGlobalEthernetIfEntry
        MAX-ACCESS not-accessible
        STATUS     current
        DESCRIPTION
        "This represents an entry in
        cLApGlobalEthernetIfTable."
        INDEX { cLApEthernetIfSlotId }
        ::= { cLApGlobalEthernetIfTable 1 }

CLApGlobalEthernetIfEntry ::= SEQUENCE {
                cLApGlobalEthernetIfCdpEnabled      TruthValue
        }

cLApGlobalEthernetIfCdpEnabled   OBJECT-TYPE
       SYNTAX      TruthValue
       MAX-ACCESS  read-write
       STATUS      current
       DESCRIPTION
            "This object is used to configure the Cisco Discovery
            Protocol(CDP) in the interface, represented by
        cLApEthernetIfSlotId of the all the APs, joined in 
        the controller.

        Setting this object to a value of 'true' would turn on 
        the CDP on this ethernet interface.

            Setting this object to a value of 'false' would turn off the
            CDP on this ethernet interface, so that CDP advertisements
            are not sent.

        Read operation on this attribute will not be supported. 
        When queried this will return a value of 'false'." 
       ::= { cLApGlobalEthernetIfEntry 1 }

cLApGlobalRetransmitCount OBJECT-TYPE
       SYNTAX      Unsigned32 
       UNITS       "retries"
       MAX-ACCESS  read-write
       STATUS      current
       DESCRIPTION
        "This object specifies the retransmission count for the
        Control Packet of all the Access Points, joined to this 
        controller. This value represents the number of packets 
        retransmitted after which the Access Point falls back to 
        another controller in case of failover."
        ::= { ciscoLwappApGlobal 14 }

cLApGlobalRetransmitTimeout OBJECT-TYPE
       SYNTAX      Unsigned32 
       UNITS       "seconds"
       MAX-ACCESS  read-write
       STATUS      current
       DESCRIPTION
        "This object specifies the retransmission timeout for the
        Control Packet of all the Access Points, joined to this 
        controller. This value represents the timeout for each 
        retransmission, during the fallback of Access Point to 
        another controller in case of failover."
       ::= { ciscoLwappApGlobal 15 }

cLApOeapDisableLocalAccess OBJECT-TYPE
       SYNTAX      TruthValue 
       MAX-ACCESS  read-write
       STATUS      current
       DESCRIPTION
          "This object specifies whether the local access is supported for
           all the Office Extended Access Points, joined to this controller. 
           If set to true, the local SSID and and LAN ports on the OEAP will
	   be disabled."
       ::= { ciscoLwappApGlobal 16 }

cLApGlobalLEDState OBJECT-TYPE
       SYNTAX      TruthValue 
       MAX-ACCESS  read-write
       STATUS      current
       DESCRIPTION
          "This object specifies whether the LED state of all the access points 
          should be enabled or disabled."
       ::= { ciscoLwappApGlobal 17 }

cLApRadioInterfaceShutdownEnabled OBJECT-TYPE
       SYNTAX      TruthValue 
       MAX-ACCESS  read-write
       STATUS      current
       DESCRIPTION
           "This object allows the user to enable or disable AP radio Interface. 
            When enabled, AP radio's will be shut down when Ethernet link 
            goes down for a duration of time set for cLApEthernetInterfaceDowntime. 
            A value of 'true' indicates the AP radio interface shutdown is enabled.
            A value of 'false' indicates the AP radio interface shutdown is disabled."
       ::= { ciscoLwappApGlobal 18 }

cLApEthernetInterfaceDowntime OBJECT-TYPE
       SYNTAX      Unsigned32
       UNITS       "Seconds"
       MAX-ACCESS  read-write
       STATUS      current
       DESCRIPTION
           "This object specifies the Ethernet interface down time after which 
            the AP radio interface will be shut down."
       ::= { ciscoLwappApGlobal 19 }

cLAPMulticastGroupAddressType OBJECT-TYPE 
       SYNTAX      InetAddressType 
       MAX-ACCESS  read-write 
       STATUS      current 
       DESCRIPTION 
          "This object specifies the AP multicast group address type."
       ::= { ciscoLwappApGlobal 20 } 
 
cLAPMulticastGroupAddress OBJECT-TYPE 
       SYNTAX      InetAddress 
       MAX-ACCESS  read-write 
       STATUS      current 
       DESCRIPTION 
          "This object specifies the AP IPv6 multicast group address."
       ::= { ciscoLwappApGlobal 21 } 

cLAPMulticastMode OBJECT-TYPE 
       SYNTAX      INTEGER {
                   unicast(1),
                   multicast(2)
             }
       MAX-ACCESS  read-write 
       STATUS      current 
       DESCRIPTION 
          "This object specifies the switch's ethernet 
           multicast support.
           unicast - Controller will convert multicast to
                     unicast packet.
           multicast - Multicast mode is enabled."
       ::= { ciscoLwappApGlobal 22 } 

cLApPrimedDiscoveryTimeout OBJECT-TYPE
		SYNTAX	INTEGER (0 | 120..43200)
        UNITS       "seconds"
		MAX-ACCESS	read-write
		STATUS		current
		DESCRIPTION
          "This object represents the primed timeout for the AP
           discovery."
		::= { ciscoLwappApGlobal 23 }

cLApGlobalPreferMode OBJECT-TYPE
      SYNTAX INTEGER {
          ipv4(1),
          ipv6(2)
      }
      MAX-ACCESS read-write
      STATUS     current
      DESCRIPTION
          "This object represents the global capwap prefer-mode"
      ::= { ciscoLwappApGlobal 24 }

cLApGlobalAPLagCapability OBJECT-TYPE
       SYNTAX      TruthValue 
       MAX-ACCESS  read-write
       STATUS      current
       DESCRIPTION
          "This object specifies whether the ap-lag capability state of all the access points 
          should be enabled or disabled."
       ::= { ciscoLwappApGlobal 25 }


--********************************************************************
-- *  AP Dot11 Interface Antenna Information
--********************************************************************
cLApDot11IfAntennaTable OBJECT-TYPE
        SYNTAX SEQUENCE OF CLApDot11IfAntennaEntry
        MAX-ACCESS not-accessible
        STATUS     current
        DESCRIPTION
                "This table represents the information about the
                basic functional parameters corresponding to
                the antenna on dot11 interfaces of the APs that have 
                joined the controller. "
        ::= { ciscoLwappApIf 4 }

cLApDot11IfAntennaEntry OBJECT-TYPE
        SYNTAX     CLApDot11IfAntennaEntry
        MAX-ACCESS not-accessible
        STATUS     current
        DESCRIPTION
                "An entry in this table represents the 802.11
                functional parameters of the dot11 interface of
                an AP that has joined the controller.

                Entries are added when the APs associate to this
                controller and deleted when they lose their
                association. " 
    INDEX           {
                        cLApSysMacAddress,
                        cLApDot11IfSlotId,
                        cLApDot11IfAntennaId
                    } 
        ::= { cLApDot11IfAntennaTable 1 }

CLApDot11IfAntennaEntry ::= SEQUENCE {
                cLApDot11IfAntennaId            Unsigned32, 
                cLApDot11IfAntennaTxEnable      TruthValue, 
                cLApDot11IfAntennaRxEnable      TruthValue, 
                cLApDot11IfAntennaEnable      TruthValue 
        }

cLApDot11IfAntennaId OBJECT-TYPE
        SYNTAX     Unsigned32 (1..3)
        MAX-ACCESS not-accessible
        STATUS     current
        DESCRIPTION
                "This object represents the antenna ID of a dot11
                interface on an AP. 
                The antenna Id for a particular dot11 interface on 
                a slot as represented by this object."
        ::= { cLApDot11IfAntennaEntry 1 }

cLApDot11IfAntennaTxEnable OBJECT-TYPE
        SYNTAX     TruthValue
        MAX-ACCESS read-write
        STATUS     current
        DESCRIPTION
                "This object specifies whether this antenna is allowed
                to trasmit or not.
                A value of 'true' enables the antenna to transmit.
                A value of 'false' disables the antenna to transmit.
                This object has been deprecated for cLApDot11IfAntennaEnable.
                cLApDot11IfAntennaTxEnable object is superseded by cLApDot11IfAntennaEnable."
        DEFVAL { true }
        ::= { cLApDot11IfAntennaEntry 2 }

cLApDot11IfAntennaRxEnable OBJECT-TYPE
        SYNTAX     TruthValue
        MAX-ACCESS read-write
        STATUS     current
        DESCRIPTION
                "This object specifies whether this antenna is allowed
                to recieve or not.
                A value of 'true' enables the antenna to receive.
                A value of 'false' disables the antenna to receive.
                This object has been deprecated for cLApDot11IfAntennaEnable.
                cLApDot11IfAntennaRxEnable object is superseded by cLApDot11IfAntennaEnable."
        DEFVAL { true }
        ::= { cLApDot11IfAntennaEntry 3 }

cLApDot11IfAntennaEnable OBJECT-TYPE
        SYNTAX     TruthValue
        MAX-ACCESS read-write
        STATUS     current
        DESCRIPTION
                "This object specifies whether this antenna is enabled
                or not.
                A value of 'true' enables the antenna.
                A value of 'false' disables the antenna."
        DEFVAL { true }
        ::= { cLApDot11IfAntennaEntry 4 }


--********************************************************************
-- *  AP Vlan Tagging
--********************************************************************
cLApVlanIfTable OBJECT-TYPE
        SYNTAX SEQUENCE OF CLApVlanIfEntry
        MAX-ACCESS not-accessible
        STATUS     current
        DESCRIPTION
                "This table represents the information about the
                basic functional parameters corresponding to
                the Ethernet interfaces of the APs that have
                joined the controller. "
        ::= { ciscoLwappApIf 5 }

cLApVlanIfEntry OBJECT-TYPE
        SYNTAX     CLApVlanIfEntry
        MAX-ACCESS not-accessible
        STATUS     current
        DESCRIPTION
                "An entry in this table represents the VLAN
                functional parameters of the Ethernet interface of
                an AP that has joined the controller.
                Entries are added when the administrator creates
                an entry in this table."
    INDEX           {
                        cLApSysMacAddress,
                        cLApVlanIfEthernetId
                    } 
        ::= { cLApVlanIfTable 1 }

CLApVlanIfEntry ::= SEQUENCE {
                cLApVlanIfEthernetId            Unsigned32,
                cLApVlanIfMode                  INTEGER,
                cLApVlanIfEnable                TruthValue,
                cLApVlanIfNativeVlanId          Unsigned32
        }

cLApVlanIfEthernetId OBJECT-TYPE
        SYNTAX     Unsigned32 (0..3)
        MAX-ACCESS not-accessible
        STATUS     current
        DESCRIPTION
                "This object represents the ID of a Ethernet
                interface on an AP."
        ::= { cLApVlanIfEntry 1 }

cLApVlanIfMode OBJECT-TYPE
        SYNTAX     INTEGER {
                      normal(1),
                      access(2),
                      trunk(3)
                   }
        MAX-ACCESS read-write
        STATUS     current
        DESCRIPTION
                "This object represents the mode this
                on this AP's Ethernet interface is
                configured for.
                    normal - VLAN is not operating in access or trunk.
                    access - VLAN is operating in access mode
                    trunk  - VLAN is operating in trunk mode."
        DEFVAL { normal }
        ::= { cLApVlanIfEntry 2 }

cLApVlanIfEnable OBJECT-TYPE
        SYNTAX     TruthValue
        MAX-ACCESS read-write
        STATUS     current
        DESCRIPTION
                "This object specifies whether this interface  is
                enabled or not.
                A value of 'true' enables the interface.
                A value of 'false' will disable the interface. This will
                delete all entries on this AP's Ethernet interface."
        DEFVAL { true }
        ::= { cLApVlanIfEntry 3 }

cLApVlanIfNativeVlanId OBJECT-TYPE
        SYNTAX     Unsigned32
        MAX-ACCESS read-write
        STATUS     current
        DESCRIPTION
                "This object represents the native VLAN ID
                assigned to this AP's Ethernet interface.
                This only applies when the icLApVlanIfMode
                is set to 'trunk'. For all other modes this
                return a value of zero."
        ::= { cLApVlanIfEntry 4 }

--********************************************************************
-- *  AP Vlan Tagging
--********************************************************************
cLApVlanListTable OBJECT-TYPE
        SYNTAX SEQUENCE OF CLApVlanListEntry
        MAX-ACCESS not-accessible
        STATUS     current
        DESCRIPTION
                "This table represents the information about the
                basic functional parameters corresponding to
                the VLAN Ethernet interfaces of the APs that have 
                joined the controller. "
        ::= { ciscoLwappApIf 6 }

cLApVlanListEntry OBJECT-TYPE
        SYNTAX     CLApVlanListEntry
        MAX-ACCESS not-accessible
        STATUS     current
        DESCRIPTION
                "An entry in this table represents the VLAN 
                functional parameters of the Ethernet interface of
                an AP that has joined the controller.
                Entries are added when the administrator creates 
                an entry in this table."
    INDEX           {
                        cLApSysMacAddress,
                        cLApVlanIfEthernetId,
                        cLApVlanListVlanId
                    } 
        ::= { cLApVlanListTable 1 }

CLApVlanListEntry ::= SEQUENCE {
                cLApVlanListVlanId        Unsigned32,
                cLApVlanListRowStatus     RowStatus
        }
cLApVlanListVlanId OBJECT-TYPE
        SYNTAX     Unsigned32 
        MAX-ACCESS not-accessible
        STATUS     current
        DESCRIPTION
                "This object represents the ID assigned to the
                VLAN on this AP's Ethernet interface."
        ::= { cLApVlanListEntry 1 }

cLApVlanListRowStatus OBJECT-TYPE
        SYNTAX     RowStatus 
        MAX-ACCESS read-create
        STATUS     current
        DESCRIPTION
                 "Used to add or delete an entry in this table."
        ::= { cLApVlanListEntry 2 }


--********************************************************************
-- *  Global AP 802.1x Supplicant Credentials
--********************************************************************
cLApGlobal802dot1xAuthenticationEnabled OBJECT-TYPE
       SYNTAX      TruthValue
       MAX-ACCESS  read-write
       STATUS      current
       DESCRIPTION
        "This object represents the Global AP 802.1x Supplicant
        Authentication feature.
        If configured as True, user can configure 8021.1x 
        authentication between lightweight access points and the 
        switch. The access point acts as an 802.1x supplicant and is 
        authenticated by the switch using EAP-FAST with anonymous 
        PAC provisioning.User can set global authentication settings 
        that all access points inherit as they join the controller. 
        This includes all access points that are currently joined to 
        the controller and any that join in the future. If desired, 
        user can override the global authentication settings and 
        assign unique authentication settings for a specific 
           access point.
           Default state is False."
        DEFVAL {false}
        ::= { ciscoLwappAp802dot1xSupplicant  1 }

cLApGlobal802dot1xSupplicantUsername OBJECT-TYPE
       SYNTAX      SnmpAdminString
       MAX-ACCESS  read-write
       STATUS      current
       DESCRIPTION
        "This object represents the 802.1x supplicant username that
        is to be inherited by all access points that join the 
        controller." 
        ::= { ciscoLwappAp802dot1xSupplicant  2}

cLApGlobal802dot1xSupplicantPassword OBJECT-TYPE
       SYNTAX      SnmpAdminString
       MAX-ACCESS  read-write
       STATUS      current
       DESCRIPTION
        "This object represents the 802.1x supplicant Password that
        is to be inherited by all access points that join the 
        controller. 
        A query on this OID will always return '****'." 
        ::= { ciscoLwappAp802dot1xSupplicant  3}

--********************************************************************
-- * Per AP 802.1x Supplicant Credentials
--********************************************************************

cLAp802dot1xSupplicantTable OBJECT-TYPE
        SYNTAX     SEQUENCE OF  CLAp802dot1xSupplicantEntry
        MAX-ACCESS not-accessible
        STATUS     current
        DESCRIPTION
        "This table provides the information about the 802.1x
        Supplicant credentials of the 802.11 LWAPP Access Points 
        that have joined the controller. Rows are added to this 
        table whenever, new APs are joined to this controller, 
        and rows are deleted whenever APs gets disjoined from 
        the controller."
        ::= { ciscoLwappAp802dot1xSupplicant  4 }

cLAp802dot1xSupplicantEntry   OBJECT-TYPE
        SYNTAX     CLAp802dot1xSupplicantEntry
        MAX-ACCESS not-accessible
        STATUS     current
        DESCRIPTION
             "Each entry in this table provides information about
             one 802.11 LWAPP Access Point that has joined the
             controller. cLApSysMacAddress is the index which
             uniquely identifies every row in the table."
        INDEX   { cLApSysMacAddress }
        ::= { cLAp802dot1xSupplicantTable 1 }

CLAp802dot1xSupplicantEntry ::= SEQUENCE {
                cLAp802dot1xSupplicantOverrideEnabled 		TruthValue,
                cLAp802dot1xSupplicantOverrideUsername 	SnmpAdminString,
                cLAp802dot1xSupplicantOverridePassword 	SnmpAdminString
        }

cLAp802dot1xSupplicantOverrideEnabled OBJECT-TYPE
       SYNTAX      TruthValue
       MAX-ACCESS  read-write
       STATUS      current
       DESCRIPTION
        "This object represents the individual AP level 802.1x
        Supplicant Authentication override parameters.
        If configured as True, user can override the Global AP 
        8021.1x authentication credentials by providing individual 
        AP level credentials.
           Default state is False."
       DEFVAL {false}
        ::= { cLAp802dot1xSupplicantEntry 1 }

cLAp802dot1xSupplicantOverrideUsername OBJECT-TYPE
       SYNTAX      SnmpAdminString
       MAX-ACCESS  read-write
       STATUS      current
       DESCRIPTION
        "This object represents the individual AP level 802.1x
        supplicant override username." 
        ::= { cLAp802dot1xSupplicantEntry 2 }

cLAp802dot1xSupplicantOverridePassword OBJECT-TYPE
       SYNTAX      SnmpAdminString
       MAX-ACCESS  read-write
       STATUS      current
       DESCRIPTION
        "This object the individual AP level 802.1x supplicant
        override password. A query on this OID will always 
        return '****'." 
        ::= { cLAp802dot1xSupplicantEntry 3}

--********************************************************************
-- *  AP WLAN Stats.
--********************************************************************

cLApWlanInfoTable OBJECT-TYPE
        SYNTAX     SEQUENCE OF CLApWlanInfoEntry
        MAX-ACCESS not-accessible
        STATUS     current
        DESCRIPTION
                "This table represents Per-AP, Per-SSID 
                information of max supported clients"
        ::= { ciscoLwappApWlanInfo 1 }

cLApWlanInfoEntry OBJECT-TYPE
        SYNTAX     CLApWlanInfoEntry
        MAX-ACCESS not-accessible
        STATUS     current
        DESCRIPTION
                "This entry contains information of
                max supported clients number"
        INDEX   {
                    cLApSysMacAddress,
                    cLWlanIndex
                }
        ::= { cLApWlanInfoTable 1 }

CLApWlanInfoEntry ::= SEQUENCE {
                cLApWlanInfoMaxClients     Unsigned32
        }

cLApWlanInfoMaxClients OBJECT-TYPE
       SYNTAX      Unsigned32(1..600)
       MAX-ACCESS  read-write
       STATUS      current
       DESCRIPTION
        "This object represents the max supported associated clients
        of a WLAN on an AP."
       DEFVAL { 600 }
        ::= { cLApWlanInfoEntry  1 }

cLApRadioWlanInfoTable OBJECT-TYPE
        SYNTAX     SEQUENCE OF CLApRadioWlanInfoEntry
        MAX-ACCESS not-accessible
        STATUS     current
        DESCRIPTION
                "This table represents Per-AP, Per-RADIO, 
                Per-SSID information."
        ::= { ciscoLwappApWlanInfo 2 }

cLApRadioWlanInfoEntry OBJECT-TYPE
        SYNTAX     CLApRadioWlanInfoEntry
        MAX-ACCESS not-accessible
        STATUS     current
        DESCRIPTION
                "This entry contains information of
                Per-AP, Per-RADIO, Per-SSID information."
        INDEX   {
                    cLApSysMacAddress,
                    cLApDot11IfSlotId,
                    cLWlanIndex
                }
        ::= { cLApRadioWlanInfoTable 1 }

CLApRadioWlanInfoEntry ::= SEQUENCE {
                cLApRadioWlanSsid       SnmpAdminString,
                cLApRadioWlanBssid      MacAddress      
        }

cLApRadioWlanSsid OBJECT-TYPE
        SYNTAX          SnmpAdminString
        MAX-ACCESS      read-only
        STATUS          current
        DESCRIPTION
            "This object represents SSID of the particular WLAN, 
            which is seen on the radio of the AP. "
        ::= { cLApRadioWlanInfoEntry 1 }

cLApRadioWlanBssid OBJECT-TYPE
        SYNTAX          MacAddress
        MAX-ACCESS      read-only
        STATUS          current
        DESCRIPTION
            "This object represents the BSSID of the SSID
             on this radio of this AP. "
        ::= { cLApRadioWlanInfoEntry 2 }

--********************************************************************
--*   Radio Level Configs
--********************************************************************

cLApDot11GlobalConfigTable OBJECT-TYPE
        SYNTAX SEQUENCE OF CLApDot11GlobalConfigEntry 
        MAX-ACCESS not-accessible
        STATUS     current
        DESCRIPTION
                "This table represents the information about the
                global attributes of the radio interface, that would be
                applicable for all the APs that join the controller. "
        ::= { ciscoLwappApIf 7 }
 
cLApDot11GlobalConfigEntry OBJECT-TYPE
        SYNTAX     CLApDot11GlobalConfigEntry
        MAX-ACCESS not-accessible
        STATUS     current
        DESCRIPTION
                "An entry in this table represents the network
                level configurations of the radio interface.
                Entries cannot be added or deleted in this table."
        INDEX { cLApDot11IfType }
        ::= { cLApDot11GlobalConfigTable 1 }

CLApDot11GlobalConfigEntry ::= SEQUENCE {
                cLApNwLegacyBeamForming INTEGER,
                cLApNwTxPowerThreshold Integer32,
                cLApNwTxPowerThresholdVer2 Integer32              
        }

cLApNwLegacyBeamForming OBJECT-TYPE
       SYNTAX      INTEGER {
                   enable(1),
                   disable(2),
                   notApplicable(3)
               }
       MAX-ACCESS  read-write
       STATUS      deprecated
       DESCRIPTION
            "This object indicates the status of legacy beam forming
            in this AP. This object is applicable only for
            11n supported APs.
            For APs that does not support legacy beam forming,
            a get request on this attribute will return
            the value 'notApplicable'.
            A value of 'enable' indicates that the legacy
            Beam forming is enabled in this AP.
            A value of 'false' indicates that the legacy
            Beam forming is disabled in this AP."
    DEFVAL          { notApplicable } 
       ::= { cLApDot11GlobalConfigEntry 1 }

cLApNwTxPowerThreshold OBJECT-TYPE
       SYNTAX      Integer32 (-80 ..-50) 
       UNITS 	   "dbm"
       MAX-ACCESS  read-write
       STATUS      current
       DESCRIPTION
        "This object represents the Global AP Transmit Power
        Threshold value. The permissible range is -80 dbm to -50 dbm"
       DEFVAL {-70}
        ::= { cLApDot11GlobalConfigEntry 2 }

cLApNwTxPowerThresholdVer2 OBJECT-TYPE
       SYNTAX      Integer32 (-80 ..-50) 
       UNITS 	   "dbm"
       MAX-ACCESS  read-write
       STATUS      current
       DESCRIPTION
        "This object represents the Global AP Transmit Power
        Threshold value when Inteference Optimal mode of 
	Tx Power Control (TPC v2) is enabled. The permissible 
	range is -80 dbm to -50 dbm"
       DEFVAL {-67}
        ::= { cLApDot11GlobalConfigEntry 3 }

--********************************************************************
-- *  AP Dot11 radio statistics Information
--********************************************************************
cLApDot11RadioStatsTable OBJECT-TYPE
        SYNTAX SEQUENCE OF CLApDot11RadioStatsEntry
        MAX-ACCESS  not-accessible
        STATUS      current
        DESCRIPTION
                "This table represents the statistics information
                 about the radios of the APs that have joined the
                 controller."
        ::= { ciscoLwappApIf 8 }

cLApDot11RadioStatsEntry OBJECT-TYPE
        SYNTAX      CLApDot11RadioStatsEntry
        MAX-ACCESS  not-accessible
        STATUS      current
        DESCRIPTION
                "An entry in this table represents a statistics of
                 the radio of an AP that has joined the conttroller.
                 
                 Entries are added when the APs associate to this 
                 controller and deleted when they lose their 
                 association."
        INDEX   {
                    cLApSysMacAddress,
                    cLApDot11IfSlotId
                }
        ::= { cLApDot11RadioStatsTable 1 }

CLApDot11RadioStatsEntry ::= SEQUENCE {
        cLApDot11RadioStatsRxErrorFrameCount        Counter32,
        cLApDot11RadioStatsMacMicErrFrameCount      Counter32,
        cLApDot11RadioStatsMacDecryptErrFrameCount  Counter32,
        cLApDot11RadioStatsRxMgmtFrameCount Counter32,
        cLApDot11RadioStatsRxCtrlFrameCount Counter32,
        cLApDot11RadioStatsRxDataFrameCount Counter32,
        cLApDot11RadioStatsTxMgmtFrameCount Counter32,
        cLApDot11RadioStatsTxCtrlFrameCount Counter32,
        cLApDot11RadioStatsTxDataFrameCount Counter32,
        cLApDot11RadioStatsRxDataPacketCount Counter32,
        cLApDot11RadioStatsTxDataPacketCount Counter32,
        cLApDot11RadioStatsRetryFrameCount   Counter32,
        cLApDot11RadioStatsRetryPacketCount  Counter32
        }

cLApDot11RadioStatsRxErrorFrameCount OBJECT-TYPE
        SYNTAX     Counter32
        UNITS      "frames"
        MAX-ACCESS read-only
        STATUS     current
        DESCRIPTION
            "This object represents the number of error frames
             received on the radio."
        ::= { cLApDot11RadioStatsEntry 1 }

cLApDot11RadioStatsMacMicErrFrameCount OBJECT-TYPE
        SYNTAX      Counter32
        UNITS       "frames"
        MAX-ACCESS  read-only
        STATUS      current
        DESCRIPTION
            "This object represents the number of frames 
             with wrong MIC received by AP on the radio."
        ::= { cLApDot11RadioStatsEntry 2 }

cLApDot11RadioStatsMacDecryptErrFrameCount OBJECT-TYPE
        SYNTAX      Counter32
        UNITS       "frames"
        MAX-ACCESS  read-only
        STATUS      current
        DESCRIPTION
            "This object represents the number of frames 
             with destroyed encrypted data received by AP
             on the radio."
        ::= { cLApDot11RadioStatsEntry 3 }

cLApDot11RadioStatsRxMgmtFrameCount OBJECT-TYPE
        SYNTAX      Counter32
        UNITS       "frames"
        MAX-ACCESS  read-only
        STATUS      current
        DESCRIPTION
                "This object represents the total number of 
                 management frame received on the radio."
        ::= { cLApDot11RadioStatsEntry 4 }
        
cLApDot11RadioStatsRxCtrlFrameCount OBJECT-TYPE
        SYNTAX      Counter32
        UNITS       "frames"
        MAX-ACCESS  read-only
        STATUS      current
        DESCRIPTION
                "This object represents the total number of 
                 control frame received on the radio."
        ::= { cLApDot11RadioStatsEntry 5 }

cLApDot11RadioStatsRxDataFrameCount OBJECT-TYPE
        SYNTAX      Counter32
        UNITS       "frames"
        MAX-ACCESS  read-only
        STATUS      current
        DESCRIPTION
                "This object represents the total number of 
                 data frame received on the radio."
        ::= { cLApDot11RadioStatsEntry 6 }
        
cLApDot11RadioStatsTxMgmtFrameCount OBJECT-TYPE
        SYNTAX      Counter32
        UNITS       "frames"
        MAX-ACCESS  read-only
        STATUS      current
        DESCRIPTION
                "This object represents the total number of 
                 management frame transmitted on the radio."
        ::= { cLApDot11RadioStatsEntry 7 }
        
cLApDot11RadioStatsTxCtrlFrameCount OBJECT-TYPE
        SYNTAX      Counter32
        UNITS       "frames"
        MAX-ACCESS  read-only
        STATUS      current
        DESCRIPTION
                "This object represents the total number of 
                 control frame transmitted on the radio."
        ::= { cLApDot11RadioStatsEntry 8 }
        
cLApDot11RadioStatsTxDataFrameCount OBJECT-TYPE
        SYNTAX      Counter32
        UNITS       "frames"
        MAX-ACCESS  read-only
        STATUS      current
        DESCRIPTION
                "This object represents the total number of 
                 data frame transmitted on the radio."
        ::= { cLApDot11RadioStatsEntry 9 }

cLApDot11RadioStatsRxDataPacketCount OBJECT-TYPE
        SYNTAX      Counter32
        UNITS       "packets"
        MAX-ACCESS  read-only
        STATUS      current
        DESCRIPTION
                "This object represents the total number of
                 data packets received on the radio."
       ::= { cLApDot11RadioStatsEntry 10 }

cLApDot11RadioStatsTxDataPacketCount OBJECT-TYPE
        SYNTAX      Counter32
        UNITS       "packets"
        MAX-ACCESS  read-only
        STATUS      current
        DESCRIPTION
                "This object represents the total number of
                 data packets transmitted on the radio."
        ::= { cLApDot11RadioStatsEntry 11 }

cLApDot11RadioStatsRetryFrameCount OBJECT-TYPE
        SYNTAX      Counter32
        UNITS       "frames"
        MAX-ACCESS  read-only
        STATUS      current
        DESCRIPTION
                "This object represents the total number of
                 downstream retry frames on the radio."
        ::= { cLApDot11RadioStatsEntry 12 }

cLApDot11RadioStatsRetryPacketCount OBJECT-TYPE
        SYNTAX      Counter32
        UNITS       "packets"
        MAX-ACCESS  read-only
        STATUS      current
        DESCRIPTION
                "This object represents the total number of
                 downstream retry packets on the radio."
        ::= { cLApDot11RadioStatsEntry 13 }

--********************************************************************
--* AP Radio Rssi Stats
--*******************************************************************
cLApDot11RadioRssiTable OBJECT-TYPE
        SYNTAX SEQUENCE OF CLApDot11RadioRssiEntry
        MAX-ACCESS not-accessible
        STATUS     current
        DESCRIPTION
                "This table represents Per AP, Per Radio Stats information
                of Average, Highest, Lowest Rssi of all the clients update
                of the APs Radio. " 
        ::= { ciscoLwappApIf 9 }

cLApDot11RadioRssiEntry OBJECT-TYPE
        SYNTAX     CLApDot11RadioRssiEntry
        MAX-ACCESS not-accessible
        STATUS     current
        DESCRIPTION
                "This entry contains stats information of
                Average, Highest and Lowest RSSI of Per AP Per Radio. "
        INDEX {
                  cLApSysMacAddress,
                  cLApDot11IfType
              }
        ::= { cLApDot11RadioRssiTable 1 }

CLApDot11RadioRssiEntry ::= SEQUENCE {
                cLApDot11RadioRssiHighest Integer32,
                cLApDot11RadioRssiLowest Integer32,
                cLApDot11RadioRssiAverage Integer32
        }

cLApDot11RadioRssiHighest OBJECT-TYPE
       SYNTAX      Integer32 
       UNITS       "dbm"
       MAX-ACCESS  read-only
       STATUS      current
       DESCRIPTION
        "This object represents the Highest Rssi value of the specific radio
        on this access point. The value '0' dbm represents no activity on this
        access point radio." 
        ::= { cLApDot11RadioRssiEntry 1 }

cLApDot11RadioRssiLowest OBJECT-TYPE
       SYNTAX      Integer32
       UNITS       "dbm"
       MAX-ACCESS  read-only
       STATUS      current
       DESCRIPTION
        "This object represents the Lowest Rssi value of the specific radio 
        on this access point. The value '0' dbm represents no activity on this
        access point radio."
        ::= { cLApDot11RadioRssiEntry 2 }

cLApDot11RadioRssiAverage OBJECT-TYPE
       SYNTAX      Integer32
       UNITS       "dbm"
       MAX-ACCESS  read-only
       STATUS      current
       DESCRIPTION
        "This object represents the Average Rssi value of the specific radio 
        on this access point. The value '0' dbm represents no activity on this
        access point radio."
        ::= { cLApDot11RadioRssiEntry 3 }

--********************************************************************
-- *  AP Crash file Info
--********************************************************************
cLApCrashInfoTable OBJECT-TYPE
        SYNTAX     SEQUENCE OF CLApCrashInfoEntry
        MAX-ACCESS not-accessible
        STATUS     current
        DESCRIPTION
                "This table represents the crash file information 
                for each AP. 
                An entry is automatically added to this table when 
                an Access Points crashes and reboots. 
                Entry is removed from this table when AP 
                disassociates from the controllers."
        ::= { ciscoLwappAp 8 }


cLApCrashInfoEntry OBJECT-TYPE
        SYNTAX     CLApCrashInfoEntry
        MAX-ACCESS not-accessible
        STATUS     current
        DESCRIPTION
                "Each entry in this table provides crash 
                information available for each AP. "
        INDEX   { cLApSysMacAddress }
        ::= { cLApCrashInfoTable 1 }

CLApCrashInfoEntry::=
        SEQUENCE {
                cLApCrashFileName  SnmpAdminString,
                cLApCrashFileSize  Unsigned32,
                cLApCrashFileTimeStamp DateAndTime
        }

cLApCrashFileName OBJECT-TYPE
       SYNTAX      SnmpAdminString (SIZE(1..28))
       MAX-ACCESS  read-only
       STATUS      current
       DESCRIPTION
               "This object indicates the crash file name for a specific AP."
       ::= {  cLApCrashInfoEntry 1 }

cLApCrashFileSize  OBJECT-TYPE
       SYNTAX      Unsigned32
       MAX-ACCESS  read-only
       STATUS      current
       DESCRIPTION
               "This object indicates the size of the crash file."    
        ::= {  cLApCrashInfoEntry 2 }

cLApCrashFileTimeStamp OBJECT-TYPE
       SYNTAX      DateAndTime
       MAX-ACCESS  read-only
       STATUS      current
       DESCRIPTION
               "This object indicates the timestamp of the crash file."
       ::= {  cLApCrashInfoEntry 3 }

cLApExtTable OBJECT-TYPE
        SYNTAX     SEQUENCE OF CLApExtEntry
        MAX-ACCESS not-accessible
        STATUS     current
        DESCRIPTION
                "This table represents the system information 
                for each AP."
        ::= { ciscoLwappAp 10 }

cLApExtEntry OBJECT-TYPE
        SYNTAX     CLApExtEntry
        MAX-ACCESS not-accessible
        STATUS     current
        DESCRIPTION
                "Each entry in this table provides system 
                information for each AP. "
        INDEX   { cLApSysMacAddress }
        ::= { cLApExtTable 1 }

CLApExtEntry::=
        SEQUENCE {
                cLApLEDFlashStatus    TruthValue,
                cLApLEDFlashDuration  Unsigned32,
                cLApInetAddressType             InetAddressType,
                cLApInetAddress                 InetAddress,
                cLApStaticIpv6AddressEnabled    TruthValue,
                cLApStaticIpv6InetAddressType   InetAddressType,
                cLApStaticIpv6InetAddress       InetAddress,
                cLApStaticIpv6PrefixLength      Unsigned32,
                cLApStaticIpv6GatewayInetAddressType InetAddressType,
                cLApStaticIpv6GatewayInetAddress    InetAddress,
                cLApStaticIpNetmaskType    InetAddressType,
                cLApStaticIpNetmask        InetAddress,
                cLApPreferMode             INTEGER,
                cLApPreferModeApplied      INTEGER
        }

cLApLEDFlashStatus    OBJECT-TYPE
       SYNTAX      TruthValue
       MAX-ACCESS  read-write
       STATUS      current
       DESCRIPTION
               "This object specifies the state of the AP LED Flash."
       ::= {  cLApExtEntry 1 }

cLApLEDFlashDuration   OBJECT-TYPE
       SYNTAX      Unsigned32
       UNITS       "seconds"
       MAX-ACCESS  read-write
       STATUS      current
       DESCRIPTION
               "This object specifies the duration for which the AP's LED should blink. 
                This is applicable when the value of cLApFlashStatus is TRUE.
                Value of 0 indicates the blinking for infinite duration."    
        ::= {  cLApExtEntry 2 }

cLApInetAddressType OBJECT-TYPE
        SYNTAX     InetAddressType
        MAX-ACCESS read-write
        STATUS     current
        DESCRIPTION
               "This object represents the type of the AP
               address made available through 
               cLApInetAddress."
        ::= { cLApExtEntry 3 }

cLApInetAddress    OBJECT-TYPE
       SYNTAX      InetAddress
       MAX-ACCESS  read-write
       STATUS      current
       DESCRIPTION
               "This object represents the address of the 
               Access Point." 
        ::= {  cLApExtEntry 4 }
     
cLApStaticIpv6AddressEnabled OBJECT-TYPE
       SYNTAX      TruthValue
       MAX-ACCESS read-write
       STATUS          current
       DESCRIPTION
            "This object when disabled implies that AP will use DHCP
            to get the IP address.  
            However, if it is enabled, then user should enter the 
            IPAddress, Netmask and Gateway."
        ::= {  cLApExtEntry 5 }

cLApStaticIpv6InetAddressType OBJECT-TYPE
        SYNTAX     InetAddressType
        MAX-ACCESS read-write
        STATUS     current
        DESCRIPTION
               "This object represents the type of the AP's
               static IPv6 address made available through 
               cLApStaticIpv6InetAddress."
        ::= { cLApExtEntry 6 }

cLApStaticIpv6InetAddress    OBJECT-TYPE
       SYNTAX      InetAddress
       MAX-ACCESS  read-write
       STATUS      current
       DESCRIPTION
               "This object represents the static IPv6 address 
               of the Access Point." 
        ::= {  cLApExtEntry 7 }   

cLApStaticIpv6PrefixLength    OBJECT-TYPE
       SYNTAX      Unsigned32 (0..128)
       MAX-ACCESS  read-write
       STATUS      current
       DESCRIPTION
               "This represents the prefix length of the static IP Address 
               configured on the AP."
        ::= {  cLApExtEntry 8 }        

cLApStaticIpv6GatewayInetAddressType  OBJECT-TYPE
       SYNTAX InetAddressType
       MAX-ACCESS read-write
       STATUS current
       DESCRIPTION
               "This represents the type of the gateway of static IPv6
               address made available through 
               cLApStaticIpv6GatewayInetAddress." 
        ::= {  cLApExtEntry 9 }        
       
cLApStaticIpv6GatewayInetAddress  OBJECT-TYPE
       SYNTAX InetAddress
       MAX-ACCESS read-write
       STATUS current
       DESCRIPTION
               "This represents the IPv6 Address of the Gateway server. 
                This attribute can be configured only if the static IP
                option is turned on in the AP."
        ::= {  cLApExtEntry 10 } 

cLApStaticIpNetmaskType OBJECT-TYPE
       SYNTAX InetAddressType
       MAX-ACCESS read-write
       STATUS current
       DESCRIPTION
               "This represents netmask type."
        ::= {  cLApExtEntry 11 }

cLApStaticIpNetmask OBJECT-TYPE
       SYNTAX InetAddress
       MAX-ACCESS read-write
       STATUS current
       DESCRIPTION
               "This represents netmask for ipv4 address."
        ::= {  cLApExtEntry 12 }


cLApPreferMode  OBJECT-TYPE
       SYNTAX INTEGER {
            ipv4(1),
            ipv6(2)
       }
       MAX-ACCESS      read-only
       STATUS          current
       DESCRIPTION
        " This object indicates capwap prefer-mode (ipv4 or ipv6) of AP."
        ::= { cLApExtEntry 13 }

cLApPreferModeApplied  OBJECT-TYPE
       SYNTAX INTEGER {
            apgroup(1),
            global(2)
       }
       MAX-ACCESS      read-only
       STATUS          current
       DESCRIPTION
        " This object indicates prefer-mode of AP applied by apgroup config or global config."
        ::= { cLApExtEntry 14 }
--********************************************************************
-- *  AP Sys Info
--********************************************************************
cLApSysInfoTable OBJECT-TYPE
        SYNTAX     SEQUENCE OF CLApSysInfoEntry
        MAX-ACCESS not-accessible
        STATUS     current
        DESCRIPTION
                "This table represents the system information 
                for each AP."
        ::= { ciscoLwappAp 9 }

cLApSysInfoEntry OBJECT-TYPE
        SYNTAX     CLApSysInfoEntry
        MAX-ACCESS not-accessible
        STATUS     current
        DESCRIPTION
                "Each entry in this table provides system 
                information for each AP. "
        INDEX   { cLApSysMacAddress }
        ::= { cLApSysInfoTable 1 }

CLApSysInfoEntry::=
        SEQUENCE {
                cLApSysMemType    SnmpAdminString,
                cLApSysMemSize    Unsigned32,
                cLApSysFlashSize  Unsigned32,
                cLApSysCpuType    SnmpAdminString,
                cLApSysFlashType  SnmpAdminString
        }

cLApSysMemType     OBJECT-TYPE
       SYNTAX      SnmpAdminString
       MAX-ACCESS  read-only
       STATUS      current
       DESCRIPTION
               "This object specifies the AP system memory type."
       ::= {  cLApSysInfoEntry 1 }

cLApSysMemSize     OBJECT-TYPE
       SYNTAX      Unsigned32
       UNITS      "KBytes"
       MAX-ACCESS  read-only
       STATUS      current
       DESCRIPTION
               "This object specifies the total AP system memory size in Kbytes."    
        ::= {  cLApSysInfoEntry 2 }

cLApSysFlashSize   OBJECT-TYPE
       SYNTAX      Unsigned32
       UNITS      "KBytes"
       MAX-ACCESS  read-only
       STATUS      current
       DESCRIPTION
               "This object specifies the AP flash size in Kbytes."
       ::= {  cLApSysInfoEntry 3 }

cLApSysCpuType     OBJECT-TYPE
       SYNTAX      SnmpAdminString
       MAX-ACCESS  read-only
       STATUS      current
       DESCRIPTION
               "This object specifies the AP cpu type"
       ::= {  cLApSysInfoEntry 4 }

cLApSysFlashType     OBJECT-TYPE
       SYNTAX      SnmpAdminString
       MAX-ACCESS  read-only
       STATUS      current
       DESCRIPTION
               "This object specifies the AP Flash type."
       ::= {  cLApSysInfoEntry 5 }

--********************************************************************
-- *  AP Dot11 radio rate statistics Information
--********************************************************************
cLApDot11RadioRateStatsTable OBJECT-TYPE
        SYNTAX SEQUENCE OF CLApDot11RadioRateStatsEntry
        MAX-ACCESS not-accessible
        STATUS     current
        DESCRIPTION
            "This table represents per AP, per radio, per rate stats information
             of all the clients of the APs Radio." 
        ::= { ciscoLwappApIf 10 }

cLApDot11RadioRateStatsEntry OBJECT-TYPE
        SYNTAX     CLApDot11RadioRateStatsEntry
        MAX-ACCESS not-accessible
        STATUS     current
        DESCRIPTION
            "This entry contains stats information of Rx/Tx packets and bytes
             of per AP per radio per rate."
        INDEX {cLApSysMacAddress,
               cLApDot11IfSlotId,
               cLApDot11RadioRate
              }
        ::= { cLApDot11RadioRateStatsTable 1 }

CLApDot11RadioRateStatsEntry ::= SEQUENCE {
        cLApDot11RadioRate                  Unsigned32,
        cLApDot11RadioRateStatsRxPackets    Counter32,
        cLApDot11RadioRateStatsRxBytes      Counter32,
        cLApDot11RadioRateStatsTxPackets    Counter32,
        cLApDot11RadioRateStatsTxBytes      Counter32,
        cLApDot11RadioRateString            SnmpAdminString
}
cLApDot11RadioRate OBJECT-TYPE
    SYNTAX          Unsigned32
    MAX-ACCESS      not-accessible
    STATUS          current
    DESCRIPTION
        "This object uniquely identifies the data rate value
        for a particular band." 
    ::= { cLApDot11RadioRateStatsEntry 1 }

cLApDot11RadioRateStatsRxPackets OBJECT-TYPE
    SYNTAX          Counter32
    MAX-ACCESS      read-only
    STATUS          current
    DESCRIPTION
        "This object represents the number of packets received for
        the specific radio and data rate on this access point." 
    ::= { cLApDot11RadioRateStatsEntry 2 }

cLApDot11RadioRateStatsRxBytes OBJECT-TYPE
    SYNTAX          Counter32
    MAX-ACCESS      read-only
    STATUS          current
    DESCRIPTION
        "This object represents the number of bytes received for
        the specific radio and data rate on this access point." 
    ::= { cLApDot11RadioRateStatsEntry 3 }

cLApDot11RadioRateStatsTxPackets OBJECT-TYPE
    SYNTAX          Counter32
    MAX-ACCESS      read-only
    STATUS          current
    DESCRIPTION
        "This object represents the number of packets transmitted from
        the specific radio and data rate on this access point." 
    ::= { cLApDot11RadioRateStatsEntry 4 }

cLApDot11RadioRateStatsTxBytes OBJECT-TYPE
    SYNTAX          Counter32
    MAX-ACCESS      read-only
    STATUS          current
    DESCRIPTION
        "This object represents the number of bytes transmitted from
        the specific radio and data rate on this access point." 
    ::= { cLApDot11RadioRateStatsEntry 5 }

cLApDot11RadioRateString OBJECT-TYPE
    SYNTAX          SnmpAdminString
    MAX-ACCESS      read-only
    STATUS          current
    DESCRIPTION
        "This object represents the data rate in a user-friendly
         text string format."
    ::= { cLApDot11RadioRateStatsEntry 6 }

cLApPacketDumpFtpServerAddressType OBJECT-TYPE
     SYNTAX      InetAddressType
     MAX-ACCESS  read-write
     STATUS      current
     DESCRIPTION
                 "This object represents the address type of
                  the Server to which the packet dump is stored."
     ::= { ciscoLwappPacketDumpInfo 1 }

cLApPacketDumpFtpServerAddress OBJECT-TYPE
     SYNTAX      InetAddress
     MAX-ACCESS  read-write
     STATUS      current
     DESCRIPTION
                 "This object represents the address of the Server to
                 which the packet dump is stored."
     ::= { ciscoLwappPacketDumpInfo 2 }

cLApPacketDumpFtpServerPath OBJECT-TYPE
     SYNTAX      SnmpAdminString
     MAX-ACCESS  read-write
     STATUS      current
     DESCRIPTION
                 "This object specifies the directory path for
                 the packet dump storing.
                 The controller remembers the last file path used."
     ::= { ciscoLwappPacketDumpInfo 3 }

cLApPacketDumpFtpUsername OBJECT-TYPE
     SYNTAX      SnmpAdminString 
     MAX-ACCESS  read-write
     STATUS      current
     DESCRIPTION
                 "This object is used to store the FTP username
                 for transferring the packet-dump to the FTP server."
     ::= { ciscoLwappPacketDumpInfo 4 }

cLApPacketDumpFtpPassword OBJECT-TYPE
     SYNTAX      SnmpAdminString 
     MAX-ACCESS  read-write
     STATUS      current
     DESCRIPTION
                 "This object is used to store the FTP password
                 for transferring the packet-dump to the FTP server."
     ::= { ciscoLwappPacketDumpInfo 5 }

cLApPacketDumpClassifier OBJECT-TYPE
     SYNTAX      BITS {
                   management(0),
                   data(1),
                   control(2),
                   dot1x(3)
                 }
     MAX-ACCESS  read-write
     STATUS      current
     DESCRIPTION
                 "This object specifies the Frame Type considered
                 for packet-dump."
     ::= { ciscoLwappPacketDumpInfo 6 }

cLApPacketDumpBufferSize OBJECT-TYPE
     SYNTAX      Unsigned32
     MAX-ACCESS  read-write
     STATUS      current
     DESCRIPTION
                 "This object specifies the buffer size considered
                 for packet-dump."
     ::= { ciscoLwappPacketDumpInfo 7 }

cLApPacketDumpCaptureTime OBJECT-TYPE
     SYNTAX      Unsigned32
     UNITS       "minutes"
     MAX-ACCESS  read-write
     STATUS      current
     DESCRIPTION
                 "This object specifies the capture time considered
                 for packet-dump."
     ::= { ciscoLwappPacketDumpInfo 8 }

cLApPacketDumpTruncation OBJECT-TYPE
     SYNTAX      Unsigned32
     UNITS       "bytes"
     MAX-ACCESS  read-write
     STATUS      current
     DESCRIPTION
                 "This object specifies the length of the packet
                 after truncation"
     ::= { ciscoLwappPacketDumpInfo 9 }

cLApPacketDumpApName OBJECT-TYPE
     SYNTAX SnmpAdminString 
     MAX-ACCESS read-write
     STATUS current
     DESCRIPTION
                "This object represents the AP name on which
                we need to start packet dump."
     ::= {  ciscoLwappPacketDumpInfo 10 }

cLApPacketDumpDeviceMacAddress OBJECT-TYPE
     SYNTAX     MacAddress
     MAX-ACCESS read-write
     STATUS     current
     DESCRIPTION
                "This object specifies the MAC address of the
                device for which we need to start packet dump on the AP."
     ::= { ciscoLwappPacketDumpInfo 11 }

cLApPacketDumpStartStop OBJECT-TYPE
     SYNTAX      INTEGER {
                  start(1),
                   stop(2),
                   none(3)
                 }
     MAX-ACCESS read-write
     STATUS     current
     DESCRIPTION
                "This object is used to start or stop, packet dump on
                the associated AP to which the particular mobile station is
                connected. When value is 'none', it indicates that
                information about current session is not available to the
                controller."
    ::= { ciscoLwappPacketDumpInfo 12 }


--********************************************************************
--* AP Radio Ssid Stats
--*******************************************************************
cLApDot11RadioSsidTable OBJECT-TYPE
    SYNTAX SEQUENCE OF CLApDot11RadioSsidEntry
    MAX-ACCESS not-accessible
    STATUS     current
    DESCRIPTION
        "This table represents Per AP, Per Radio information
        of Ssid of all the neighbor APs updating
        the APs Radio. " 
    ::= { ciscoLwappApIf 11 }

cLApDot11RadioSsidEntry OBJECT-TYPE
    SYNTAX     CLApDot11RadioSsidEntry
    MAX-ACCESS not-accessible
    STATUS     current
    DESCRIPTION
        "This entry contains ssid information of
        Neighbor APs of Per AP Per Radio. "
    INDEX {
            cLApSysMacAddress,
            cLApDot11IfType,
            cLApSsidIndex
    }
    ::= { cLApDot11RadioSsidTable 1 }

CLApDot11RadioSsidEntry ::= SEQUENCE {
    cLApSsidIndex             Unsigned32,
    cLApDot11RadioSsidName    OCTET STRING
    }

cLApSsidIndex OBJECT-TYPE
    SYNTAX      Unsigned32
    MAX-ACCESS  not-accessible
    STATUS      current
    DESCRIPTION
        "This object indicates the index of the ssid
        detected by Per AP Per Radio." 
    ::= { cLApDot11RadioSsidEntry 1 }

cLApDot11RadioSsidName OBJECT-TYPE
    SYNTAX      OCTET STRING (SIZE  (1..32))
    MAX-ACCESS  read-only
    STATUS      current
    DESCRIPTION
        "This object represents the ssid name of the neighbor AP
        on this access point." 
    ::= { cLApDot11RadioSsidEntry 2 }

--********************************************************************
--* AP Cable Modem Stats
--*******************************************************************
cLApCableModemIfStatsTable OBJECT-TYPE
        SYNTAX SEQUENCE OF CLApCableModemIfStatsEntry
        MAX-ACCESS not-accessible
        STATUS     current
        DESCRIPTION
            "This table represents the statistics of cable
             modem interface per AP when the CM connected to the AP."
        ::= { ciscoLwappApIf 12 }

cLApCableModemIfStatsEntry OBJECT-TYPE
        SYNTAX     CLApCableModemIfStatsEntry
        MAX-ACCESS not-accessible
        STATUS     current
        DESCRIPTION
            "This entry contains stats information of cable modem
             per AP"
        INDEX { cLApSysMacAddress }
        ::= { cLApCableModemIfStatsTable 1 }

CLApCableModemIfStatsEntry ::= SEQUENCE {
        cLApCmMacAddress             SnmpAdminString,
        cLApCmApMacAddress           SnmpAdminString,
        cLApCmSwVersion              SnmpAdminString,
        cLApEthernetSpeed            SnmpAdminString,
        cLApEthernetStatus           SnmpAdminString,
        cLApCmStatus                 SnmpAdminString,
        cLApCmSerialNumber           SnmpAdminString,
        cLApCmUsChannelStatus        SnmpAdminString,
        cLApCmDsChannelStatus        SnmpAdminString,
        cLApCmMaskBit                SnmpAdminString        
}

cLApCmMacAddress OBJECT-TYPE
    SYNTAX          SnmpAdminString 
    MAX-ACCESS      read-only
    STATUS          current
    DESCRIPTION
        "This object uniquely identifies the MAC address 
         of the Cable Modem that has been connected to
         the AP."
    ::= { cLApCableModemIfStatsEntry 1 }

cLApCmApMacAddress OBJECT-TYPE
    SYNTAX          SnmpAdminString
    MAX-ACCESS      read-only
    STATUS          current
    DESCRIPTION
        "This object uniquely identifies the interface
         of Ethernet MAC address of the AP where 
         the Cable Modem is connected."
    ::= { cLApCableModemIfStatsEntry 2 }

cLApCmSwVersion OBJECT-TYPE
    SYNTAX          SnmpAdminString
    MAX-ACCESS      read-only
    STATUS          current
    DESCRIPTION
        "This object represents the software version 
         of the Cable Modem that has been connected to
         the AP."
    ::= { cLApCableModemIfStatsEntry 3 }

cLApEthernetSpeed OBJECT-TYPE
    SYNTAX          SnmpAdminString
    MAX-ACCESS      read-only
    STATUS          current
    DESCRIPTION
        "This object represents the Ethernet speed 
         of the Cable Modem that has been connected to
         the AP."
    ::= { cLApCableModemIfStatsEntry 4 }

cLApEthernetStatus OBJECT-TYPE
    SYNTAX          SnmpAdminString
    MAX-ACCESS      read-only
    STATUS          current
    DESCRIPTION
        "This object represents the Ethernet status
         of the Cable Modem that has been connected to
         the AP."
    ::= { cLApCableModemIfStatsEntry 5 }


cLApCmStatus OBJECT-TYPE
    SYNTAX          SnmpAdminString
    MAX-ACCESS      read-only
    STATUS          current
    DESCRIPTION
        "This object represents the status of the
         Cable Modem that has been connected to
         the AP."
    ::= { cLApCableModemIfStatsEntry 6 }


cLApCmSerialNumber OBJECT-TYPE
    SYNTAX          SnmpAdminString
    MAX-ACCESS      read-only
    STATUS          current
    DESCRIPTION
        "This object represents the Serial Number 
         of the Cable Modem that has been connected to
         the AP."
    ::= { cLApCableModemIfStatsEntry 7 }

cLApCmUsChannelStatus OBJECT-TYPE
    SYNTAX          SnmpAdminString
    MAX-ACCESS      read-only
    STATUS          current
    DESCRIPTION
        "This object represents the UpStream Channel 
         Status of the Cable Modem that has been 
         connected to the AP."
    ::= { cLApCableModemIfStatsEntry 8 }

cLApCmDsChannelStatus OBJECT-TYPE
    SYNTAX          SnmpAdminString
    MAX-ACCESS      read-only
    STATUS          current
    DESCRIPTION
        "This object represents the DownStream Channel  
         Status of the Cable Modem that has been 
         connected to the AP."
    ::= { cLApCableModemIfStatsEntry 9 }


cLApCmMaskBit OBJECT-TYPE
    SYNTAX     SnmpAdminString
    MAX-ACCESS read-only
    STATUS     current
    DESCRIPTION
        "This object represents the Mask Bit 
         of the Cable Modem based on the mask
         value the CM statistics is displayed 
	 for the AP."
    ::= { cLApCableModemIfStatsEntry 10 }

-- ********************************************************************
-- *    AP Environmental information
-- ********************************************************************

cLApEnvInfoTable OBJECT-TYPE
   SYNTAX          SEQUENCE OF CLApEnvInfoEntry
   MAX-ACCESS      not-accessible
   STATUS          current
   DESCRIPTION
       "This table represents information about temperature
         degree state and orientation of the AP"
    ::= { ciscoLwappAp 11 }

cLApEnvInfoEntry OBJECT-TYPE
    SYNTAX          CLApEnvInfoEntry
    MAX-ACCESS      not-accessible
    STATUS          current
    DESCRIPTION
        "Each entry represents a conceptual row in this table.
        An entry is created when MAP joins the controller.
        The entry is removed when the mesh node lose their
        association with the controller due to loss of
        communication with controller or when a mesh node
        is reset."
    INDEX           { cLApSysMacAddress }
    ::= { cLApEnvInfoTable 1 }

CLApEnvInfoEntry ::= SEQUENCE {
        cLApEnvTemperatureDegree             SnmpAdminString,
        cLApEnvTemperatureState              INTEGER,
        cLApEnvOrientation                   INTEGER,
        cLApEnvPoeOutStatus                  INTEGER
}

cLApEnvTemperatureDegree  OBJECT-TYPE
    SYNTAX          SnmpAdminString
    MAX-ACCESS      read-only
    STATUS          current
    DESCRIPTION
        "This object represents temperature
        of the AP in both celcius and fahrenheit."
    ::= { cLApEnvInfoEntry 1 }

cLApEnvTemperatureState  OBJECT-TYPE
    SYNTAX          INTEGER {
                      unknown(0),
                      green(1),
                      yellow(2),
                      red(3)
                }
    MAX-ACCESS      read-only
    STATUS          current
    DESCRIPTION
        "This object represents temperature state
        of the AP."
    ::= { cLApEnvInfoEntry 2 }


cLApEnvOrientation  OBJECT-TYPE
    SYNTAX          INTEGER {
                      unknown(0),
                      vertical(1),
                      horizontal(2)
                   }
    MAX-ACCESS      read-only
    STATUS          current
    DESCRIPTION
        "This object represents orientation
        of the AP."
    ::= { cLApEnvInfoEntry 3 }

cLApEnvPoeOutStatus  OBJECT-TYPE
    SYNTAX          INTEGER {
                      unknown(1),
                      on(2),
                      off(3)
                   }
    MAX-ACCESS      read-only
    STATUS          current
    DESCRIPTION
        "This object represents POE out status
        of the AP."
    ::= { cLApEnvInfoEntry 4 }


-- ********************************************************************
-- *    GPS related information
-- ********************************************************************

cLApGpsInfoTable OBJECT-TYPE
   SYNTAX          SEQUENCE OF CLApGpsInfoEntry 
    MAX-ACCESS      not-accessible
    STATUS          current
    DESCRIPTION
        "This table represents information about location and
        velocity parameters received from the GPS module on the
       LWAPP Access Points that have joined the controller."
    ::= { ciscoLwappAp 12 }

cLApGpsInfoEntry OBJECT-TYPE
    SYNTAX          CLApGpsInfoEntry 
    MAX-ACCESS      not-accessible
    STATUS          current
    DESCRIPTION
        "Each entry represents a conceptual row in this table.
        An entry is created when AP joins the controller.
        The entry is removed when the AP lose their
        association with the controller due to loss of
        communication with controller"
    INDEX           { cLApSysMacAddress }
    ::= { cLApGpsInfoTable 1 }

CLApGpsInfoEntry ::= SEQUENCE {
        cLApGpsLocationPresent       TruthValue,
        cLApGpsLocationValid         TruthValue,
        cLApGpsLatitude              SnmpAdminString,
        cLApGpsLongitude             SnmpAdminString,
        cLApGpsAltitude              SnmpAdminString,
        cLApGpsCollectionTime        TimeStamp
}


cLApGpsLocationPresent OBJECT-TYPE
    SYNTAX          TruthValue
    MAX-ACCESS      read-only
    STATUS          current 
    DESCRIPTION
        "This object indicates whether the access point
        has the GPS module installed or not."
    ::= { cLApGpsInfoEntry 1 }

cLApGpsLocationValid OBJECT-TYPE
    SYNTAX          TruthValue
    MAX-ACCESS      read-only
    STATUS          current 
    DESCRIPTION
        "This object indicates whether the location
        information is valid or not."
    ::= { cLApGpsInfoEntry 2 }

cLApGpsLatitude  OBJECT-TYPE
 SYNTAX          SnmpAdminString
    MAX-ACCESS      read-only
    STATUS          current 
    DESCRIPTION
        "This object represents latitude information
        in the GPS data received."
    ::= { cLApGpsInfoEntry 3 }

cLApGpsLongitude  OBJECT-TYPE
    SYNTAX          SnmpAdminString
    MAX-ACCESS      read-only
    STATUS          current 
    DESCRIPTION
        "This object represents longitude information
        in the GPS data received."
    ::= { cLApGpsInfoEntry 4 }


cLApGpsAltitude  OBJECT-TYPE
    SYNTAX          SnmpAdminString
    MAX-ACCESS      read-only
    STATUS          current 
    DESCRIPTION
        "This object represents altitude information
        in the GPS data received."
    ::= { cLApGpsInfoEntry 5 }

cLApGpsCollectionTime OBJECT-TYPE
SYNTAX          TimeStamp
    MAX-ACCESS      read-only
    STATUS          current 
    DESCRIPTION
        "This object represents the time when GPS
        data was collected."
    ::= { cLApGpsInfoEntry 6 }


--********************************************************************
-- *  Notification Objects 
--********************************************************************
cLApAssocFailureReason OBJECT-TYPE
        SYNTAX     CLApAssocFailureReason 
        MAX-ACCESS accessible-for-notify
        STATUS     current
        DESCRIPTION
                "This object specifies the failure reasons when
                a AP fails to associate with a controller."
        ::= { ciscoLwappApMIBNotifObjects 1 }

cLApRogueApMacAddress OBJECT-TYPE
        SYNTAX     MacAddress
        MAX-ACCESS accessible-for-notify
        STATUS     current
        DESCRIPTION
                "This object represents the radio MAC address 
                common to the dot11 interfaces of the rogue AP."
        ::= {  ciscoLwappApMIBNotifObjects 2}

cLApDot11RadioChannelNumber OBJECT-TYPE
        SYNTAX     CLDot11Channel
        MAX-ACCESS accessible-for-notify
        STATUS     current
        DESCRIPTION
                "This object represents the channel number of the
                 radio interface of the AP, represented by 
                 cLApDot11IfType."
        ::= {  ciscoLwappApMIBNotifObjects 3}

cLApRogueApSsid OBJECT-TYPE
        SYNTAX     SnmpAdminString
        MAX-ACCESS accessible-for-notify
        STATUS     current
        DESCRIPTION
                "This object represents the SSID used by the
                 rogue AP to intrude the network." 
        ::= {  ciscoLwappApMIBNotifObjects 4}

cLApRogueType OBJECT-TYPE
    SYNTAX          INTEGER  {
                        asleap(1),
                          honeypot (2),
                        other(3)
                    }
        MAX-ACCESS accessible-for-notify
        STATUS     current
        DESCRIPTION
                "This object represents the SSID of the used by the
                 rogue AP to intrude the network."
        ::= {  ciscoLwappApMIBNotifObjects 5}

cLApWipsReason OBJECT-TYPE
        SYNTAX     INTEGER {
                     noMonitoringDevice(1)
                   }
        MAX-ACCESS accessible-for-notify
        STATUS     current
        DESCRIPTION
                "This object specifies the failure reasons for an AP
                 when cLApWipsEnable is set to 'true'.

         noMonitoringDevice - No monitoring device 
         connected to collect WIPs information." 
        ::= { ciscoLwappApMIBNotifObjects 6 }

cLApWipsClear OBJECT-TYPE
        SYNTAX     TruthValue
        MAX-ACCESS accessible-for-notify
        STATUS     current
        DESCRIPTION
                "This object specifies whether this event is 
                raise or clear.
                A value of 'true' indicates this event is cleared
                A value of 'false' indicates this even is raised."
        ::= { ciscoLwappApMIBNotifObjects 7 }

cLApIfUpDownFailureType OBJECT-TYPE
        SYNTAX     INTEGER {
                     detectedFailure(1),
                     configuredReset(2)
                   }
		
        MAX-ACCESS accessible-for-notify
        STATUS     current
        DESCRIPTION
                "This object specifies the type of the
		 AP interface failure.
        detectedFailure(1) - Failure of radio.
        configuredReset(2) - Reset due to manual 
				       configuration." 
        ::= { ciscoLwappApMIBNotifObjects 8 }

cLApIfUpDownCause OBJECT-TYPE
        SYNTAX     DisplayString
        MAX-ACCESS accessible-for-notify
        STATUS     current
        DESCRIPTION
                "This object specifies the cause of the
		 AP interface failure." 
        ::= { ciscoLwappApMIBNotifObjects 9 }

cLApIfUpDownFailureCode OBJECT-TYPE
        SYNTAX     DisplayString
        MAX-ACCESS accessible-for-notify
        STATUS     current
        DESCRIPTION
                "This object specifies the code of the
		 AP interface failure." 
        ::= { ciscoLwappApMIBNotifObjects 10 }

cLApAlarmSet OBJECT-TYPE
        SYNTAX     TruthValue
        MAX-ACCESS accessible-for-notify
        STATUS     current
        DESCRIPTION
                "This object specifies whether this event is
                raise or clear.
                A value of 'true' indicates this event is set.
                A value of 'false' indicates this even is cleared."
        ::= { ciscoLwappApMIBNotifObjects 11 }

cLApRogueClassType OBJECT-TYPE
        SYNTAX          INTEGER  {
                                  pending(0),
                                  friendly(1),
                                  malicious(2),
                                  unclassified(3),
                                  custom(4)
                                 }
        MAX-ACCESS accessible-for-notify
		STATUS     current
	    DESCRIPTION
	         "This object specifies the AP class type of the 
                  Rogue AP detected."
		::= {  ciscoLwappApMIBNotifObjects 12}

cLApRogueDetectedChannel OBJECT-TYPE
        SYNTAX CLDot11Channel
        MAX-ACCESS accessible-for-notify
        STATUS     current
        DESCRIPTION
             "This object represents the rogue
               detected channel number."
        ::= {  ciscoLwappApMIBNotifObjects 13}			   

cLApRSSI OBJECT-TYPE
        SYNTAX Integer32
        MAX-ACCESS accessible-for-notify
        STATUS     current
        DESCRIPTION
               "This object specifies the Rogue RSSI as seen by 
                AP Interface."
        ::= {  ciscoLwappApMIBNotifObjects 14}

cLApSNR OBJECT-TYPE
        SYNTAX Integer32
        MAX-ACCESS accessible-for-notify
        STATUS     current
        DESCRIPTION
               "This object specifies the SNR seen by AP 
                Interface from Rogue"
        ::= {  ciscoLwappApMIBNotifObjects 15}

cLApDot11RadioCurrentChannel OBJECT-TYPE
        SYNTAX     CLDot11Channel
        MAX-ACCESS accessible-for-notify
        STATUS     current
        DESCRIPTION
            "This object represents the dot11 
             current channel."		
        ::= {  ciscoLwappApMIBNotifObjects 16}		 	 

cLApAdhocRogue OBJECT-TYPE
        SYNTAX INTEGER  {
                         no(0),
                         yes(1)
                        }
         MAX-ACCESS accessible-for-notify
         STATUS     current
         DESCRIPTION
             "This object represents the flag used to state if 
              the rogue found is an Adhoc rogue or it is an AP."
         ::= {  ciscoLwappApMIBNotifObjects 17} 

cLApRogueAPOnWiredNetwork OBJECT-TYPE
        SYNTAX INTEGER  {
                        no(0),
                        yes(1)
                        }

        MAX-ACCESS accessible-for-notify
        STATUS     current
        DESCRIPTION
             "This object represents the flag used to state if 
              the rogue is found on the wired network.
              A value of '1' indicates Rogue AP is found on wired
              network.
              A value of '0' indicates Rogue AP is not found
              on wired network."
         ::= {  ciscoLwappApMIBNotifObjects 18} 

cLApRogueMode OBJECT-TYPE
        SYNTAX INTEGER  {
                         initializing(0),
                         pending(1),
                         alert(2),
                         detectedLrad(3),
                         known(4),
                         acknowledge(5),
                         contained(6), 
                         threat(7),
                         containedPending(8), 
                         knownContained(9),
                         trustedMissing(10)
                        }
         MAX-ACCESS accessible-for-notify
         STATUS     current
         DESCRIPTION
             "This attribute is use to specify the state in which 
                 the Rogue AP is user can set the Rogue AP in alert, 
                 known or acknowledge state.

                 Alert state means Rogue AP can be a potential threat,
                 trap will be sent out to trap recipients. 

                 Known state means its just internal AP which is not 
                 on the same Switch.  

                 Acknowledge state means an external AP whose
                 existence is acceptable and not a threat (probably 
                 some other company's AP).

                 Contained means containement is initiated and ongoing.
                 Threat is usually the state when the rogue is found 
                 on wired network.

                 known(4), knownContained(9) and trustedMissing(10) 
                 will appear in known rogue list.
                 known rogues can be pre provisioned and known rogues 
                 state can be changed to alert(2)."
         ::= {  ciscoLwappApMIBNotifObjects 19 } 			  

cLApRogueIsClassifiedByRule OBJECT-TYPE
         SYNTAX      TruthValue
         MAX-ACCESS accessible-for-notify
         STATUS     current
         DESCRIPTION
             "This object represents the flag used to state if the 
              rogue is classified by a rogue rule.
              A value of 'true' indicates its classifed by rogue rule.
              A value of 'false' indicates its not classified by rogue 
              rule."
         ::= {  ciscoLwappApMIBNotifObjects 20 }

cLApRogueClassifiedApMacAddress OBJECT-TYPE
        SYNTAX     MacAddress
        MAX-ACCESS accessible-for-notify
        STATUS     current
        DESCRIPTION
                "This object represents the radio MAC address 
                of the classified rogue AP."
        ::= {  ciscoLwappApMIBNotifObjects 21 }

cLApRogueClassifiedRSSI OBJECT-TYPE
         SYNTAX Integer32
         MAX-ACCESS accessible-for-notify
         STATUS     current
         DESCRIPTION
             "This object represents the Rogue classified RSSI as 
              seen by Airespace AP Interface."
         ::= {  ciscoLwappApMIBNotifObjects 22 }

cLAPPreviousMonitorMode OBJECT-TYPE
    SYNTAX     CLApMode
    MAX-ACCESS accessible-for-notify
    STATUS current
    DESCRIPTION
        "This object represents the previous AP monitor Mode."
    ::= {   ciscoLwappApMIBNotifObjects 23 }

cLAPCurrentMonitorMode OBJECT-TYPE
    SYNTAX     CLApMode
    MAX-ACCESS accessible-for-notify
    STATUS current
    DESCRIPTION
        "This object represents the current AP monitor Mode."
    ::= {   ciscoLwappApMIBNotifObjects 24 }

cLApSsidKeyConfSsidA OBJECT-TYPE
         SYNTAX SnmpAdminString
         MAX-ACCESS accessible-for-notify
         STATUS     current
         DESCRIPTION
             "This object represents the SSID which has same
              cipher key with another SSID on the same AP.
              The another SSID is represented by cLApSsidKeyConfSsidB." 
         ::= {  ciscoLwappApMIBNotifObjects 25 }

cLApSsidKeyConfKeyIdxA OBJECT-TYPE
         SYNTAX Unsigned32
         MAX-ACCESS accessible-for-notify
         STATUS     current
         DESCRIPTION
             "This object represents key index of the SSID which has same
              cipher key with another SSID on the same AP.
              It is the key index of cLApSsidKeyConfSsidA.
              The another SSID is represented by cLApSsidKeyConfSsidB." 
         ::= {  ciscoLwappApMIBNotifObjects 26 }

cLApSsidKeyConfSsidB OBJECT-TYPE
         SYNTAX SnmpAdminString
         MAX-ACCESS accessible-for-notify
         STATUS     current
         DESCRIPTION
             "This object represents the SSID which has same
              cipher key with another SSID on the same AP.
              The another SSID is represented by cLApSsidKeyConfSsidA." 
         ::= {  ciscoLwappApMIBNotifObjects 27 }

cLApSsidKeyConfKeyIdxB OBJECT-TYPE
         SYNTAX Unsigned32
         MAX-ACCESS accessible-for-notify
         STATUS     current
         DESCRIPTION
             "This object represents key index of the SSID which has same
              cipher key with another SSID on the same AP.
              It is the key index of cLApSsidKeyConfSsidB.
              The another SSID is represented by cLApSsidKeyConfSsidA." 
         ::= {  ciscoLwappApMIBNotifObjects 28 }

cLApPreviousChannel       OBJECT-TYPE
        SYNTAX     Unsigned32
        MAX-ACCESS accessible-for-notify
        STATUS     current
        DESCRIPTION
            "This object represents the channel before changed."
        ::= {  ciscoLwappApMIBNotifObjects 29 }

cLApCurrentChannel      OBJECT-TYPE
        SYNTAX     Unsigned32
        MAX-ACCESS accessible-for-notify
        STATUS     current
        DESCRIPTION
        "This object represents the channel after changed."
        ::= {  ciscoLwappApMIBNotifObjects 30 }

cLApChannelCustomize     OBJECT-TYPE
        SYNTAX     INTEGER
                {
                    automatic(1),
                    customized(2)
                }
        MAX-ACCESS accessible-for-notify
        STATUS     current
        DESCRIPTION
        "This object represents the channel's change mode. 
        If this value is true, then bsnAPDot11CurrentChannel in
        bsnAPIfDot11PhyDSSSTable is assigned by dynamic
        algorithm and is read-only."
        ::= {  ciscoLwappApMIBNotifObjects 31 }

cLApIfLoadChannelUtilization OBJECT-TYPE
    SYNTAX     INTEGER (0..65535)
    MAX-ACCESS accessible-for-notify
    STATUS     current
    DESCRIPTION
        "This object specifies the code of the
         AP Interface channel load utilization."
    ::= { ciscoLwappApMIBNotifObjects 32 }
 
cLAPGroupVlanName OBJECT-TYPE
    SYNTAX     OCTET STRING (SIZE (0..255))
    MAX-ACCESS accessible-for-notify
    STATUS     current
    DESCRIPTION
        "This object specifies the code of the
         AP Group Interface Name."
    ::= { ciscoLwappApMIBNotifObjects 33 }

cLApRuleName OBJECT-TYPE
    SYNTAX          SnmpAdminString (SIZE(1..32))
    MAX-ACCESS      accessible-for-notify 
    STATUS          current
    DESCRIPTION
        "This object represents the rule name to identify
        applied on the Ap."
    ::= { ciscoLwappApMIBNotifObjects 34 }

cLApSeverityScore OBJECT-TYPE
    SYNTAX          Unsigned32
    MAX-ACCESS      accessible-for-notify 
    STATUS          current
    DESCRIPTION
        "This object is used to define the custom classification
         severity score of the rules.
         This object is applicable when cLRuleRogueType is configured
         as 'custom'."
    ::= { ciscoLwappApMIBNotifObjects 35  }

cLApDot11XorRadioRoleChangeReason OBJECT-TYPE
    SYNTAX          INTEGER {
                        none(1),
                        auto(2),
                        manual(3) 
                     }   
    MAX-ACCESS      accessible-for-notify
    STATUS          current
    DESCRIPTION
        "This object is used to identify the reason code for 
         radio role change of XOR radio."
     ::= { ciscoLwappApMIBNotifObjects 36 }

--********************************************************************
-- *  Notifications 
--********************************************************************
ciscoLwappApIfRegulatoryDomainMismatchNotif NOTIFICATION-TYPE
    OBJECTS         {
                        cLApName,
                        cLApDot11IfType,
                        cLApDot11IfRegDomain,
                        cldRegulatoryDomain
                    }
     STATUS current
     DESCRIPTION
         "This notification  is generated if an AP radio's regulatory
          domain doesn't match the country the controller is configured
          for.  Due to the mismatch, the AP will fail to associate with
          the controller."
     ::= { ciscoLwappApMIBNotifs 1 }

ciscoLwappApCrash NOTIFICATION-TYPE
    OBJECTS { cLApName }
    STATUS obsolete -- superceded by ciscoLwappApAssociated trap
    DESCRIPTION
        "This notification is generated after an AP rejoins the
        controller after  a crash. Once the AP joins, the controller
        will get the crash file from the AP and sends this 
        notification."
    ::= { ciscoLwappApMIBNotifs 2 }

ciscoLwappApUnsupported NOTIFICATION-TYPE
    OBJECTS         {
                        cLApName,
                        cLApAssocFailureReason
                    }
    STATUS current
    DESCRIPTION
        "This notification is generated after an unsupported AP tries
        to join the controller."
    ::= { ciscoLwappApMIBNotifs 3 }


ciscoLwappApAssociated NOTIFICATION-TYPE
    OBJECTS         {
                        cLApName,
              cLApLastRebootReason,
			  cLApDataEncryptionStatus
            }
    STATUS current
    DESCRIPTION
        "This notification is generated whenever an AP joins the
        controller successfully. This notification contains 
        information about the last reboot reason and Data 
        Encryption status of the AP."
    ::= { ciscoLwappApMIBNotifs 4 }

ciscoLwappApPower NOTIFICATION-TYPE
    OBJECTS         {
                        cLApName,
              cLApPowerStatus
            }
    STATUS current
    DESCRIPTION
        "This notification is generated whenever an AP detects low 
        power from Ethernet."
    ::= { ciscoLwappApMIBNotifs 5 }

ciscoLwappApRogueApDetected NOTIFICATION-TYPE
    OBJECTS         {
                        cLApSysMacAddress,
              cLApName,
              cLApRogueApMacAddress,
              cLApEthernetIfSlotId,
              cLApDot11IfType, 
              cLApDot11RadioChannelNumber,
              cLApRogueApSsid,
              cLApRogueType              
            }
    STATUS current
    DESCRIPTION
        "This notification is generated whenever a rogue AP is
        detected."
    ::= { ciscoLwappApMIBNotifs 6 }

ciscoLwappApRogueApCleared NOTIFICATION-TYPE
    OBJECTS         {
                        cLApSysMacAddress,
              cLApName,
              cLApRogueApMacAddress,
              cLApEthernetIfSlotId,
              cLApDot11IfType, 
              cLApDot11RadioChannelNumber,
              cLApRogueApSsid,
              cLApRogueType
            }
    STATUS current
    DESCRIPTION
        "This notification is generated whenever a rogue AP was
        detected and then subsequently if its been removed from 
        the network."
    ::= { ciscoLwappApMIBNotifs 7 }

ciscoLwappApWipsNotification NOTIFICATION-TYPE
    OBJECTS         {
                        cLApName,
              cLApWipsReason,
              cLApWipsClear
            }
    STATUS current
    DESCRIPTION
        "This notification is generated whenever a controller
         detects a WIPS event."
    ::= { ciscoLwappApMIBNotifs 8 }

ciscoLwappApNoDownlinkChannelNotify NOTIFICATION-TYPE
    OBJECTS { cLApName }
    STATUS     current
    DESCRIPTION
        "This notification is generated when ever AP fails to find
         new downlink channel."
    ::= { ciscoLwappApMIBNotifs 9 }

ciscoLwappApIfUpNotify NOTIFICATION-TYPE
    OBJECTS         {
                        cLApSysMacAddress,
                        cLApDot11IfSlotId,
                        cLApPortNumber,
                        cLApIfUpDownFailureType,
                        cLApIfUpDownCause,
                        cLApIfUpDownFailureCode,
                        cLApName
                    }
    STATUS     current
    DESCRIPTION
        "This notification is generated when AP's Interface
	 operational status goes up."
    ::= { ciscoLwappApMIBNotifs 10 }

ciscoLwappApIfDownNotify NOTIFICATION-TYPE
    OBJECTS         {
                        cLApSysMacAddress,
                        cLApDot11IfSlotId,
                        cLApAdminStatus,
                        cLApDot11IfAdminStatus,
                        cLApIfUpDownFailureType,
                        cLApIfUpDownCause,
                        cLApIfUpDownFailureCode,
                        cLApName
                    }
    STATUS     current
    DESCRIPTION
        "This notification is generated when AP's Interface
	 operational status goes down."
    ::= { ciscoLwappApMIBNotifs 11 }

ciscoLwappApClientThresholdNotify NOTIFICATION-TYPE
    OBJECTS         {
                        cLApSysMacAddress,
                        cLApName,
                        cLApDot11IfSlotId,
                        cLApDot11IfType, 
                        cLRFProfileHighDensityMaxRadioClients,
                        cLRFProfileHDClientTrapThreshold 
                    }
    STATUS     current
    DESCRIPTION
        "This notification is generated when the number of
	 clients on the AP's Radio Interface exceeds
	 the limit defined in cLRFProfileHDClientTrapThreshold."
    ::= { ciscoLwappApMIBNotifs 12 }

ciscoLwappApUpgradeFailureNotify NOTIFICATION-TYPE
    OBJECTS         {
                        cLApSysMacAddress,
                        cLApName,
                        cLApUpgradeFromVersion,
                        cLApUpgradeToVersion,
                        cLApUpgradeFailureCause
                    }
    STATUS     current
    DESCRIPTION
        "This notification is generated when AP image upgrade failed."
    ::= { ciscoLwappApMIBNotifs 13 }

ciscoLwappApCpuUsageHigh NOTIFICATION-TYPE
    OBJECTS {
                cLApSysMacAddress,
                cLApName,
                cLApCpuCurrentUsage,
                cLApAlarmSet
            }
    STATUS current
    DESCRIPTION
        "When an AP detects its CPU usage is higher than the
         threshold configured in clsSysApCpuUsageThreshold, 
         this notification is generated with cLApAlarmSet
         set to true. When this AP's CPU usage falls below
         the threshold lately, this notification is
         generated with cLApAlarmSet set to false."
    ::= { ciscoLwappApMIBNotifs 14 }

ciscoLwappApMemoryUsageHigh NOTIFICATION-TYPE
    OBJECTS {
                cLApSysMacAddress,
                cLApName,
                cLApMemoryCurrentUsage,
                cLApAlarmSet
            }
    STATUS current
    DESCRIPTION
        "When an AP detects its memory usage is higher than the
         threshold configured in clsSysApMemoryUsageThreshold,
         this notification is generated with cLApAlarmSet
         set to true. When this AP's memory usage falls below
         the threshold lately, this notification is
         generated with cLApAlarmSet set to false."
    ::= { ciscoLwappApMIBNotifs 15 }

ciscoLwappApMaxClientLimitNotify NOTIFICATION-TYPE
    OBJECTS         {
                        cLApSysMacAddress,
                        cLApName,
                        cLApDot11IfSlotId,
                        cLApMaxClientLimitNumberTrap,
                        cLApMaxClientLimitCause,
                        cLApMaxClientLimitSet
                    }
    STATUS     current
    DESCRIPTION
        "This notification is generated when the event that 
         max client limit reached is raised or cleared."
		::= { ciscoLwappApMIBNotifs 16 }

ciscoLwappApAdjChannelRogueDetected NOTIFICATION-TYPE
    OBJECTS         {
                     cLApSysMacAddress,
                     cLApName,
                     cLApRogueApMacAddress,
                     cLApEthernetIfSlotId,
                     cLApDot11IfType,
                     cLApRogueDetectedChannel,
                     cLApRSSI,
                     cLApSNR,
                     cLApDot11RadioCurrentChannel,
                     cLApAdhocRogue,					  
                     cLApRogueApSsid,
                     cLApRogueClassType
                    }
    STATUS current
    DESCRIPTION
         "This notification is generated whenever a rogue AP is
          detected at the Adjacent channels"
    ::= { ciscoLwappApMIBNotifs 17 }  

ciscoLwappApAdjChannelRogueCleared NOTIFICATION-TYPE
    OBJECTS         {
                     cLApSysMacAddress,
                     cLApName,
                     cLApRogueApMacAddress,
                     cLApEthernetIfSlotId,
                     cLApDot11IfType,
                     cLApRogueDetectedChannel,
                     cLApDot11RadioCurrentChannel					 
                    }
    STATUS current
    DESCRIPTION
         "This notification is generated whenever a rogue AP is
          detected at the Adjacent channels and then
          subsequently if its been removed from the network."
    ::= { ciscoLwappApMIBNotifs 18 }		  

ciscoLwappApRogueDetected NOTIFICATION-TYPE
    OBJECTS         {
                     cLApSysMacAddress,
                     cLApName,
                     cLApRogueApMacAddress,
                     cLApEthernetIfSlotId,
                     cLApDot11IfType,
                     cLApRogueDetectedChannel,
                     cLApRSSI,
                     cLApSNR,
                     cLApRogueAPOnWiredNetwork,
                     cLApAdhocRogue,					  
                     cLApRogueApSsid,
                     cLApRogueClassType,
                     cLApRogueMode,
                     cLApRogueIsClassifiedByRule,
                     cLApSeverityScore,
                     cLApRuleName,
                     cLApRogueClassifiedApMacAddress,
                     cLApRogueClassifiedRSSI
                    }
    STATUS current
    DESCRIPTION
         "This notification is generated whenever a rogue AP is
          detected at the same channel."
    ::= { ciscoLwappApMIBNotifs 19 }

ciscoLwappApCurrentChannelRogueDetected NOTIFICATION-TYPE
    OBJECTS         {
                     cLApSysMacAddress,
                     cLApName,
                     cLApRogueApMacAddress,
                     cLApEthernetIfSlotId,
                     cLApDot11IfType,
                     cLApRogueDetectedChannel,
                     cLApRSSI,
                     cLApSNR,
                     cLApDot11RadioCurrentChannel,
                     cLApAdhocRogue,
                     cLApRogueApSsid,
                     cLApRogueClassType
                   }
    STATUS current
    DESCRIPTION
        "This notification is generated whenever a rogue AP is
         detected at the Current channel."
    ::= { ciscoLwappApMIBNotifs 20 }

ciscoLwappApCurrentChannelRogueCleared NOTIFICATION-TYPE
     OBJECTS         {
                      cLApSysMacAddress,
                      cLApName,
                      cLApRogueApMacAddress,
                      cLApEthernetIfSlotId,
                      cLApDot11IfType,
                      cLApRogueDetectedChannel,
                      cLApDot11RadioCurrentChannel
                     }
     STATUS current
     DESCRIPTION
         "This notification is generated whenever a rogue AP is
          detected at the Current channels and then
          subsequently if its been removed from the network."
     ::= { ciscoLwappApMIBNotifs 21 }		  

ciscoLwappApMonitorModeChangeNotify NOTIFICATION-TYPE
    OBJECTS         {
                        cLApSysMacAddress,
                        cLApName,
                        cLAPPreviousMonitorMode,
                        cLAPCurrentMonitorMode 
                    }
    STATUS     current
    DESCRIPTION
        "This notification is generated when the event that 
         AP monitor mode changed."
    ::= { ciscoLwappApMIBNotifs 22 }

ciscoLwappApAcTimeSyncFailureTrap  NOTIFICATION-TYPE
     OBJECTS         {
                      cLApSysMacAddress,
                      cLApName
                     } 
     STATUS current
     DESCRIPTION
         "This notification is generated when the heartbeat between
          AP and Controller is lost or connection broken."
     ::={ ciscoLwappApMIBNotifs 23 }

ciscoLwappApSsidKeyConflict NOTIFICATION-TYPE
     OBJECTS         {
                      cLApSysMacAddress,
                      cLApIfMacAddress,
                      cLApSsidKeyConfSsidA,
                      cLApSsidKeyConfKeyIdxA,
                      cLApSsidKeyConfSsidB,
                      cLApSsidKeyConfKeyIdxB
                     }
     STATUS current
     DESCRIPTION
         "This notification is generated whenever 2 SSIDs
          on same AP have same cipher key. "
     ::= { ciscoLwappApMIBNotifs 24 }

ciscoLwappApCurrChannelChanged NOTIFICATION-TYPE
    OBJECTS       {
                    cLApSysMacAddress,
                    cLApName,
                    cLApDot11IfSlotId,
                    cLApPreviousChannel,
                    cLApCurrentChannel,
                    cLApChannelCustomize
                  }
    STATUS current
    DESCRIPTION
         "This notification is generated when the channel is changed 
         by automatic or customized."
    ::= { ciscoLwappApMIBNotifs 25 }

ciscoLwappApCapwapRetransmissionQueueFullEvent     NOTIFICATION-TYPE
     OBJECTS {
                 cLApSysMacAddress
             }
     STATUS     current
     DESCRIPTION
             "This notification will be sent whenever capwap retransmission 
              queue for an AP is filled."
     ::= { ciscoLwappApMIBNotifs 26 }

ciscoLwappApSystemBootupEvent  NOTIFICATION-TYPE
     OBJECTS {
                 cLApSysMacAddress
             }
     STATUS     current
     DESCRIPTION
             "EUR This notification will be sent whenever System
              Boots Up."
     ::= { ciscoLwappApMIBNotifs 27 }

ciscoLwappXmFilterCheckWarning  NOTIFICATION-TYPE
     OBJECTS {
                 cLApName
             }
     STATUS     current
     DESCRIPTION
             "This notification will be sent whenever 
              Co-existence filter is Not present "
     ::= { ciscoLwappApMIBNotifs 28 }


ciscoLwappApModeUnsupportedOnFlexExpressEvent NOTIFICATION-TYPE
     OBJECTS {
                 cLApSysMacAddress
             }
     STATUS     current
     DESCRIPTION
             "This notification will be sent whenever ap with unsupported mode joins flexexpress wlc or virtual wlc" 
     ::= { ciscoLwappApMIBNotifs 29 }

ciscoLwappRadioRoleChangeNotify  NOTIFICATION-TYPE
     OBJECTS {
               cLApSysMacAddress,
               cLApName,
               cLApDot11IfSlotId, 
               cLApDot11XorRadioBand,
               cLApDot11XorRadioRoleChangeReason
             }
     STATUS  current
     DESCRIPTION
           "This notification will be sent whenever XOR radio of AP is changed its Radio role"
     ::= { ciscoLwappApMIBNotifs 30 }     

--********************************************************************
--*    Compliance statements  
--********************************************************************

ciscoLwappApMIBCompliances OBJECT IDENTIFIER
        ::= { ciscoLwappApMIBConform 1 }

ciscoLwappApMIBGroups OBJECT IDENTIFIER
        ::= { ciscoLwappApMIBConform 2 }

--STATUS deprecated by ciscoLwappApMIBCompliance
ciscoLwappApMIBCompliance MODULE-COMPLIANCE
        STATUS     deprecated 
        DESCRIPTION
                "The compliance statement for the SNMP entities that
                implement the ciscoLwappApMIB module. "
    MODULE          -- this module
    MANDATORY-GROUPS {
                ciscoLwappApGroup,
                ciscoLwappApIfGroup
        }
        ::= { ciscoLwappApMIBCompliances 1 }

--STATUS deprecated by ciscoLwappApMIBComplianceRev2
ciscoLwappApMIBComplianceRev1 MODULE-COMPLIANCE
        STATUS     deprecated 
        DESCRIPTION
                "The compliance statement for the SNMP entities that
                implement the ciscoLwappApMIB module. "
    MODULE          -- this module
    MANDATORY-GROUPS {
                ciscoLwappApGroup,
                ciscoLwappApIfGroup,
                ciscoLwappApGroupSup1
        }
        ::= { ciscoLwappApMIBCompliances 2 }

--STATUS deprecated by ciscoLwappApMIBComplianceRev3
ciscoLwappApMIBComplianceRev2 MODULE-COMPLIANCE
        STATUS     deprecated 
        DESCRIPTION
                "The compliance statement for the SNMP entities that
                implement the ciscoLwappApMIB module. "
    MODULE          -- this module
    MANDATORY-GROUPS {
                ciscoLwappApGroup,
                ciscoLwappApIfGroup,
                ciscoLwappApGroupSup1,
                ciscoLwappApGroupSup2
        }
        ::= { ciscoLwappApMIBCompliances 3 }

-- Added since last MIB approval
ciscoLwappApMIBComplianceRev3 MODULE-COMPLIANCE
        STATUS     deprecated 
        DESCRIPTION
                "The compliance statement for the SNMP entities that
                implement the ciscoLwappApMIB module. "
    MODULE          -- this module
    MANDATORY-GROUPS {
                ciscoLwappApGroup,
                ciscoLwappApIfGroup,
                ciscoLwappApGroupSup1,
                ciscoLwappApGroupSup2,
                ciscoLwappApGroupSup3,
                ciscoLwappApGroupSup4,
                ciscoLwappApNotifObjsGroup,
                ciscoLwappApNotifsGroup,
                ciscoLwappApGroupSup4,
                ciscoLwappApEthernetIfGroup,
                ciscoLwappApRadioGroup
        }
        ::= { ciscoLwappApMIBCompliances 4 }
  
-- Added for Franciscan release
ciscoLwappApMIBComplianceRev4 MODULE-COMPLIANCE
        STATUS          deprecated
        DESCRIPTION
                "The compliance statement for the SNMP entities that
                implement the ciscoLwappApMIB module. "
    MODULE          -- this module
    MANDATORY-GROUPS {
                ciscoLwappApGroup,
                ciscoLwappApIfGroup,
                ciscoLwappApGroupSup1,
                ciscoLwappApGroupSup2,
                ciscoLwappApGroupSup3,
                ciscoLwappApNotifObjsGroup,
                ciscoLwappApNotifsGroup,
                ciscoLwappApGroupSup4,
                ciscoLwappApEthernetIfGroup,
                ciscoLwappApRadioGroup,
                ciscoLwappApGroupSup5
        }
        ::= { ciscoLwappApMIBCompliances 5 }

ciscoLwappApMIBComplianceRev5 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroup,
                        ciscoLwappApGroupSup4,
                        ciscoLwappApEthernetIfGroup,
                        ciscoLwappApRadioGroup,
                        ciscoLwappApGroupSup5,
                        ciscoLwappSeClientSup
                    }
    ::= { ciscoLwappApMIBCompliances 6 }

ciscoLwappApMIBComplianceRev6 MODULE-COMPLIANCE
    STATUS          deprecated
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroup,
                        ciscoLwappApGroupSup4,
                        ciscoLwappApEthernetIfGroup,
                        ciscoLwappApRadioGroup,
                        ciscoLwappApGroupSup5,
                        ciscoLwappSeClientSup
                    }
    ::= { ciscoLwappApMIBCompliances 7 }
ciscoLwappApMIBComplianceRev7 MODULE-COMPLIANCE
    STATUS          current
    DESCRIPTION
        "The compliance statement for the SNMP entities that
        implement the ciscoLwappApMIB module."
    MODULE          -- this module
    MANDATORY-GROUPS {
                        ciscoLwappApGroup,
                        ciscoLwappApIfGroup,
                        ciscoLwappApGroupSup1,
                        ciscoLwappApGroupSup2,
                        ciscoLwappApGroupSup3,
                        ciscoLwappApNotifObjsGroup,
                        ciscoLwappApNotifsGroupVer1,
                        ciscoLwappApGroupSup6,
                        ciscoLwappApGroupSup7,
                        ciscoLwappApEthernetIfGroup,
                        ciscoLwappApRadioGroup,
                        ciscoLwappApGroupSup5,
                        ciscoLwappSeClientSup,
                        ciscoLwappDot11IfAntennaGroup,
                        ciscoLwappRetransmitGroup
                    }

    OBJECT          cLApDot11IfAntennaEnable
    MIN-ACCESS      read-only
    DESCRIPTION
        "Write access is not required."

    OBJECT          cLApRetransmitCount
    MIN-ACCESS      read-only
    DESCRIPTION
        "Write access is not required."

    OBJECT          cLApRetransmitTimeout
    MIN-ACCESS      read-only
    DESCRIPTION
        "Write access is not required."

    OBJECT          cLApGlobalRetransmitCount
    MIN-ACCESS      read-only
    DESCRIPTION
        "Write access is not required."

    OBJECT          cLApGlobalRetransmitTimeout
    MIN-ACCESS      read-only
    DESCRIPTION
        "Write access is not required."

    OBJECT          cLApName
    MIN-ACCESS      read-only
    DESCRIPTION
        "Write access is not required."

    OBJECT          cLApPrimaryControllerAddress
    MIN-ACCESS      read-only
    DESCRIPTION
        "Write access is not required."

    OBJECT          cLApSecondaryControllerAddress
    MIN-ACCESS      read-only
    DESCRIPTION
        "Write access is not required."

    OBJECT          cLApTertiaryControllerAddress
    MIN-ACCESS      read-only
    DESCRIPTION
        "Write access is not required."

    OBJECT          cLApEncryptionEnable
    MIN-ACCESS      read-only
    DESCRIPTION
        "Write access is not required."

    OBJECT          cLApFailoverPriority
    MIN-ACCESS      read-only
    DESCRIPTION
        "Write access is not required."

    OBJECT          cLApTelnetEnable
    MIN-ACCESS      read-only
    DESCRIPTION
        "Write access is not required."

    OBJECT          cLApSshEnable
    MIN-ACCESS      read-only
    DESCRIPTION
        "Write access is not required."

    OBJECT          cLApPreStdStateEnabled
    MIN-ACCESS      read-only
    DESCRIPTION
        "Write access is not required."

    OBJECT          cLApPwrInjectorStateEnabled
    MIN-ACCESS      read-only
    DESCRIPTION
        "Write access is not required."

    OBJECT          cLApPwrInjectorSelection
    MIN-ACCESS      read-only
    DESCRIPTION
        "Write access is not required."

    OBJECT          cLApPwrInjectorSwMacAddr
    MIN-ACCESS      read-only
    DESCRIPTION
        "Write access is not required."

    OBJECT          cLApWipsEnable
    MIN-ACCESS      read-only
    DESCRIPTION
        "Write access is not required."

    OBJECT          cLApMonitorModeOptimization
    MIN-ACCESS      read-only
    DESCRIPTION
        "Write access is not required."

    OBJECT          cLApDomainName
    MIN-ACCESS      read-only
    DESCRIPTION
        "Write access is not required."

    OBJECT          cLApNameServerAddress
    MIN-ACCESS      read-only
    DESCRIPTION
        "Write access is not required."

    OBJECT          cLApAMSDUEnable
    MIN-ACCESS      read-only
    DESCRIPTION
        "Write access is not required."

    OBJECT          cLApEncryptionSupported
    MIN-ACCESS      read-only
    DESCRIPTION
        "Write access is not required."

    OBJECT          cLApRogueDetectionEnabled
    MIN-ACCESS      read-only
    DESCRIPTION
        "Write access is not required."

    OBJECT          cLApTcpMss
    MIN-ACCESS      read-only
    DESCRIPTION
        "Write access is not required."

    OBJECT          cLApAdminStatus
    MIN-ACCESS      read-only
    DESCRIPTION
        "Write access is not required."

    OBJECT          cLAp11nChannelBandwidth
    MIN-ACCESS      read-only
    DESCRIPTION
        "Write access is not required."

    OBJECT          cLApLomEnabled
    MIN-ACCESS      read-only
    DESCRIPTION
        "Write access is not required."

    OBJECT          cLApLomFirstChannel
    MIN-ACCESS      read-only
    DESCRIPTION
        "Write access is not required."

    OBJECT          cLApLomSecondChannel
    MIN-ACCESS      read-only
    DESCRIPTION
        "Write access is not required."

    OBJECT          cLApLomThirdChannel
    MIN-ACCESS      read-only
    DESCRIPTION
        "Write access is not required."

    OBJECT          cLApLomFourthChannel
    MIN-ACCESS      read-only
    DESCRIPTION
        "Write access is not required."

    OBJECT          cLApLegacyBeamForming
    MIN-ACCESS      read-only
    DESCRIPTION
        "Write access is not required."

    OBJECT          cLApCdpOverAirEnabled
    MIN-ACCESS      read-only
    DESCRIPTION
        "Write access is not required."

    OBJECT          cLApDot11IfAdminStatus
    MIN-ACCESS      read-only
    DESCRIPTION
        "Write access is not required."

    OBJECT          cLApEthernetIfAdminStatus
    MIN-ACCESS      read-only
    DESCRIPTION
        "Write access is not required."

    OBJECT          cLApEthernetIfCdpEnabled
    MIN-ACCESS      read-only
    DESCRIPTION
        "Write access is not required."

    OBJECT          cLApCredentialGlobalUserName
    MIN-ACCESS      read-only
    DESCRIPTION
        "Write access is not required."

    OBJECT          cLApCredentialGlobalPassword
    MIN-ACCESS      read-only
    DESCRIPTION
        "Write access is not required."

    OBJECT          cLApCredentialGlobalSecret
    MIN-ACCESS      read-only
    DESCRIPTION
        "Write access is not required."

    OBJECT          cLApLinkLatencyEnable
    MIN-ACCESS      read-only
    DESCRIPTION
        "Write access is not required."

    OBJECT          cLApLinkLatencyReset
    MIN-ACCESS      read-only
    DESCRIPTION
        "Write access is not required."

    OBJECT          cLApCountryCode
    MIN-ACCESS      read-only
    DESCRIPTION
        "Write access is not required."

    OBJECT          ciscoLwappApIfRegulatoryDomainMismatchNotifEnabled
    MIN-ACCESS      read-only
    DESCRIPTION
        "Write access is not required."

    OBJECT          ciscoLwappApCrashEnabled
    MIN-ACCESS      read-only
    DESCRIPTION
        "Write access is not required."

    OBJECT          ciscoLwappApUnsupportedEnabled
    MIN-ACCESS      read-only
    DESCRIPTION
        "Write access is not required."

    OBJECT          ciscoLwappApAssociatedEnabled
    MIN-ACCESS      read-only
    DESCRIPTION
        "Write access is not required."

    OBJECT          cLApPrimaryDiscoveryTimeout
    MIN-ACCESS      read-only
    DESCRIPTION
        "Write access is not required."

    OBJECT          cLApFastHbTimerTimeout
    MIN-ACCESS      read-only
    DESCRIPTION
        "Write access is not required."

    OBJECT          cLApFastHbTimerEnabled
    MIN-ACCESS      read-only
    DESCRIPTION
        "Write access is not required."

    OBJECT          cLApGlobalPrimaryControllerAddress
    MIN-ACCESS      read-only
    DESCRIPTION
        "Write access is not required."

    OBJECT          cLApGlobalSecondaryControllerAddress
    MIN-ACCESS      read-only
    DESCRIPTION
        "Write access is not required."

    OBJECT          cLApGlobalPrimaryControllerName
    MIN-ACCESS      read-only
    DESCRIPTION
        "Write access is not required."

    OBJECT          cLApGlobalSecondaryControllerName
    MIN-ACCESS      read-only
    DESCRIPTION
        "Write access is not required."

    OBJECT          cLApGlobalPrimaryControllerAddressType
    MIN-ACCESS      read-only
    DESCRIPTION
        "Write access is not required."

    OBJECT          cLApGlobalSecondaryControllerAddressType
    MIN-ACCESS      read-only
    DESCRIPTION
        "Write access is not required."

    OBJECT          cLApGlobalFailoverPriority
    MIN-ACCESS      read-only
    DESCRIPTION
        "Write access is not required."

    OBJECT          cLApGlobalTcpMss
    MIN-ACCESS      read-only
    DESCRIPTION
        "Write access is not required."

    OBJECT          cLApGlobalDot11IfCdpEnabled
    MIN-ACCESS      read-only
    DESCRIPTION
        "Write access is not required."

    OBJECT          cLApGlobalEthernetIfCdpEnabled
    MIN-ACCESS      read-only
    DESCRIPTION
        "Write access is not required."

    OBJECT          cLApVlanIfMode
    MIN-ACCESS      read-only
    DESCRIPTION
        "Write access is not required."

    OBJECT          cLApVlanIfEnable
    MIN-ACCESS      read-only
    DESCRIPTION
        "Write access is not required."

    OBJECT          cLApVlanIfNativeVlanId
    MIN-ACCESS      read-only
    DESCRIPTION
        "Write access is not required."

    OBJECT          cLApPrimaryControllerAddressType
    MIN-ACCESS      read-only
    DESCRIPTION
        "Write access is not required."

    OBJECT          cLApSecondaryControllerAddressType
    MIN-ACCESS      read-only
    DESCRIPTION
        "Write access is not required."

    OBJECT          cLApTertiaryControllerAddressType
    MIN-ACCESS      read-only
    DESCRIPTION
        "Write access is not required."

    OBJECT          cLApGlobal802dot1xAuthenticationEnabled
    MIN-ACCESS      read-only
    DESCRIPTION
        "Write access is not required."

    OBJECT          cLApGlobal802dot1xSupplicantPassword
    MIN-ACCESS      read-only
    DESCRIPTION
        "Write access is not required."

    OBJECT          cLApGlobal802dot1xSupplicantUsername
    MIN-ACCESS      read-only
    DESCRIPTION
        "Write access is not required."

    OBJECT          cLAp802dot1xSupplicantOverrideEnabled
    MIN-ACCESS      read-only
    DESCRIPTION
        "Write access is not required."

    OBJECT          cLAp802dot1xSupplicantOverrideUsername
    MIN-ACCESS      read-only
    DESCRIPTION
        "Write access is not required."

    OBJECT          cLAp802dot1xSupplicantOverridePassword
    MIN-ACCESS      read-only
    DESCRIPTION
        "Write access is not required."

    OBJECT          cLApNwLegacyBeamForming
    MIN-ACCESS      read-only
    DESCRIPTION
        "Write access is not required."

    OBJECT          cLApNwTxPowerThreshold
    MIN-ACCESS      read-only
    DESCRIPTION
        "Write access is not required."

    OBJECT          cLApCredentialUserName
    MIN-ACCESS      read-only
    DESCRIPTION
        "Write access is not required."

    OBJECT          cLApCredentialPassword
    MIN-ACCESS      read-only
    DESCRIPTION
        "Write access is not required."

    OBJECT          cLApCredentialSecret
    MIN-ACCESS      read-only
    DESCRIPTION
        "Write access is not required."

    OBJECT          cLApCredentialEnableGlobalCredentials
    MIN-ACCESS      read-only
    DESCRIPTION
        "Write access is not required."

    OBJECT          cLApVlanListRowStatus
    MIN-ACCESS      read-only
    DESCRIPTION
        "Write access is not required."

    OBJECT          cLAdjChannelRogueEnabled
    MIN-ACCESS      read-only
    DESCRIPTION
        "Write access is not required."	
    ::= { ciscoLwappApMIBCompliances 8 }

--********************************************************************
--*    Units of conformance  
--********************************************************************

ciscoLwappApGroup OBJECT-GROUP
        OBJECTS {
                cLApIfMacAddress,
                cLApMaxNumberOfDot11Slots,
                cLApIfSmtDot11Bssid
        }                
        STATUS  current
        DESCRIPTION
                "This collection of objects represents the information
                about the general attributes and functional 
                parameters of those APs that have joined the
                controller. "
        ::= { ciscoLwappApMIBGroups 1 }

ciscoLwappApIfGroup OBJECT-GROUP
    OBJECTS         { cLApDot11IfType }
        STATUS  current
        DESCRIPTION
                "This collection of objects represents the information
                about the dot11 interfaces of those APs that have 
                joined the controller. "
        ::= { ciscoLwappApMIBGroups 2 }

ciscoLwappApGroupSup1 OBJECT-GROUP
    OBJECTS         { cLApEntPhysicalIndex }
        STATUS  current
        DESCRIPTION
                "This supplemental collection of objects represents the
                information about the general attributes and functional 
                parameters of those APs that have joined the
                controller. "
        ::= { ciscoLwappApMIBGroups 3 }

ciscoLwappApGroupSup2 OBJECT-GROUP
    OBJECTS         { cLApName }
        STATUS  current
        DESCRIPTION
                 "This supplemental collection of objects represents the
                  name associated with those APs that have joined the
                  controller."
        ::= { ciscoLwappApMIBGroups 4 }

ciscoLwappApGroupSup3 OBJECT-GROUP
        OBJECTS {
                  cLApDot11IfRegDomain, 
                  cLApDot11nSupport, 
                  cLAp11nChannelBandwidth,
                  cLApCountryCode, 
                  cLApCountryAllowed 
        }                
        STATUS  current
        DESCRIPTION
                 "This supplemental collection of objects represents the
                  country and 802.11n related information for those APs 
                  that have joined the controller."
        ::= { ciscoLwappApMIBGroups 5 }


ciscoLwappApNotifObjsGroup OBJECT-GROUP
    OBJECTS         { cLApAssocFailureReason }
        STATUS  current
        DESCRIPTION
                "This supplemental collection of objects represents the
                information carried by the AP related notifications 
                sent by the agent to a network management station. "
        ::= { ciscoLwappApMIBGroups 6 }

ciscoLwappApNotifsGroup NOTIFICATION-GROUP
        NOTIFICATIONS {
                  ciscoLwappApIfRegulatoryDomainMismatchNotif,
                  ciscoLwappApCrash, 
                  ciscoLwappApUnsupported,
                  ciscoLwappApAssociated
        }                
    STATUS          deprecated
        DESCRIPTION
                "This supplemental collection of objects represents the
                AP related notifications sent by the agent to a network
                management station.
                ciscoLwappApNotifsGroup object is superseded by ciscoLwappApNotifsGroupVer1."
        ::= { ciscoLwappApMIBGroups 7 }

ciscoLwappApGroupSup4 OBJECT-GROUP
        OBJECTS {
                  cLApUpTime, 
                  cLLwappUpTime,
                  cLLwappJoinTakenTime,  
                  cLApMaxNumberOfEthernetSlots, 
                  cLApPrimaryControllerAddressType, 
                  cLApPrimaryControllerAddress,
                  cLApSecondaryControllerAddressType,
                  cLApSecondaryControllerAddress,
                  cLApTertiaryControllerAddressType,
                  cLApTertiaryControllerAddress,
                  cLApLomEnabled,
                  cLApLomFirstChannel,
                  cLApLomSecondChannel,
                  cLApLomThirdChannel, 
                  cLApLomFourthChannel,
                  cLApCredentialGlobalUserName,
                  cLApCredentialGlobalPassword,
                  cLApCredentialGlobalSecret,
                  cLApCredentialUserName,
                  cLApCredentialPassword,
                  cLApCredentialSecret,
                  cLApCredentialEnableGlobalCredentials,
                  cLApFastHbTimerTimeout,
                  cLApFastHbTimerEnabled,
                  cLApPrimaryDiscoveryTimeout,
                  cLApGlobalPrimaryControllerAddressType,
                  cLApGlobalPrimaryControllerAddress,
                  cLApGlobalPrimaryControllerName,
                  cLApGlobalSecondaryControllerAddressType,
                  cLApGlobalSecondaryControllerAddress,
                  cLApGlobalSecondaryControllerName,
                  ciscoLwappApIfRegulatoryDomainMismatchNotifEnabled,
                  ciscoLwappApCrashEnabled, 
                  ciscoLwappApUnsupportedEnabled,
                  ciscoLwappApAssociatedEnabled,
                  cLApLastRebootReason,
                  cLApPrimedDiscoveryTimeout

        }                
    STATUS          deprecated
        DESCRIPTION
                 "This supplemental collection of objects represents the
                  global and credential information for those APs 
                  that have joined the controller.
                  ciscoLwappApGroupSup4 object is superseded by ciscoLwappApGroupSup6."
        ::= { ciscoLwappApMIBGroups 8 }

ciscoLwappApEthernetIfGroup OBJECT-GROUP
        OBJECTS {
                cLApEthernetIfName,
                cLApEthernetIfMacAddress,
                cLApEthernetIfAdminStatus,
                cLApEthernetIfOperStatus,
                cLApEthernetIfRxUcastPkts,
                cLApEthernetIfRxNUcastPkts,
                cLApEthernetIfTxUcastPkts,
                cLApEthernetIfTxNUcastPkts
        }
        STATUS  current
        DESCRIPTION
                "This collection of objects represents the information
                about the Ethernet interfaces of those APs that have
                joined the controller. "
        ::= { ciscoLwappApMIBGroups 9 }

ciscoLwappApRadioGroup OBJECT-GROUP
        OBJECTS {
                        cLApDot11RadioMACAddress,
                cLApDot11RadioSubBand,
                cLApDot11RadioVersion,
		cLApDot11IsBackhaul,
		cLApDot11RadioRole,
                cLApDot11RadioMode,
                cLApDot11RadioSubType
        }
        STATUS  current
        DESCRIPTION
                "This collection of objects represents the information
                about the Radios of those APs that have
                joined the controller. "
        ::= { ciscoLwappApMIBGroups 10 }


ciscoLwappApGroupSup5 OBJECT-GROUP
        OBJECTS {
                  cLApGlobalFailoverPriority, 
                  cLApFailoverPriority, 
                  cLApEncryptionEnable,
                  cLApLinkLatencyEnable,
                  cLApLinkLatencyReset,
                  cLApLinkLatencyStatsCurrent,
                  cLApLinkLatencyStatsMin,
                  cLApLinkLatencyStatsMax,
                  cLApLinkLatencyTimeStamp                  
        }                
        STATUS  current
        DESCRIPTION
                 "This supplemental collection of objects represents 
                 objects related to encryption and link latency of 
                 AP."
        ::= { ciscoLwappApMIBGroups 11 }

ciscoLwappSeClientSup OBJECT-GROUP
    OBJECTS         {
                        cLApSeClientUserName,
                        cLApSeClientIPAddrType,
                        cLApSeClientIPAddr,
                        cLApSeClientDuration,
                        cLApSeClientPort
                    }
    STATUS          current
    DESCRIPTION
        "This supplemental collection of objects represents the
        Spectrum Expert client details connected to the APs."
    ::= { ciscoLwappApMIBGroups 12 }

ciscoLwappDot11IfAntennaGroup OBJECT-GROUP
    OBJECTS         { cLApDot11IfAntennaEnable }
    STATUS          current
    DESCRIPTION
        "This supplemental collection of objects represents the
        antenna details corresponding to the dot11 interface of the
        Access Points."
    ::= { ciscoLwappApMIBGroups 13 }

ciscoLwappRetransmitGroup OBJECT-GROUP
    OBJECTS         {
                        cLApRetransmitCount,
                        cLApRetransmitTimeout,
                        cLApGlobalRetransmitCount,
                        cLApGlobalRetransmitTimeout
                    }
    STATUS          current
    DESCRIPTION
        "This supplemental collection of objects represents the
        retransmit parameters corresponding to the fallback of an
        AccessPoint to another controller during failover."
    ::= { ciscoLwappApMIBGroups 14 }

ciscoLwappApGroupSup6 OBJECT-GROUP
    OBJECTS         {
                        cLApUpTime,
                        cLLwappUpTime,
                        cLLwappJoinTakenTime,
                        cLApMaxNumberOfEthernetSlots,
                        cLApPrimaryControllerAddressType,
                        cLApPrimaryControllerAddress,
                        cLApSecondaryControllerAddressType,
                        cLApSecondaryControllerAddress,
                        cLApTertiaryControllerAddressType,
                        cLApTertiaryControllerAddress,
                        cLApLomFirstChannel,
                        cLApLomSecondChannel,
                        cLApLomThirdChannel,
                        cLApLomFourthChannel,
                        cLApCredentialGlobalUserName,
                        cLApCredentialGlobalPassword,
                        cLApCredentialGlobalSecret,
                        cLApCredentialUserName,
                        cLApCredentialPassword,
                        cLApCredentialSecret,
                        cLApCredentialEnableGlobalCredentials,
                        cLApFastHbTimerTimeout,
                        cLApFastHbTimerEnabled,
                        cLApPrimaryDiscoveryTimeout,
                        cLApGlobalPrimaryControllerAddressType,
                        cLApGlobalPrimaryControllerAddress,
                        cLApGlobalPrimaryControllerName,
                        cLApGlobalSecondaryControllerAddressType,
                        cLApGlobalSecondaryControllerAddress,
                        cLApGlobalSecondaryControllerName,
                        ciscoLwappApIfRegulatoryDomainMismatchNotifEnabled,
                        ciscoLwappApCrashEnabled,
                        ciscoLwappApUnsupportedEnabled,
                        ciscoLwappApAssociatedEnabled,
                        cLApLastRebootReason,
                        cLApPrimedDiscoveryTimeout,
                        cLApGlobalPreferMode
                    }
    STATUS          current
    DESCRIPTION
        "This supplemental collection of objects represents the
        global and credential information for those APs 
        that have joined the controller."
    ::= { ciscoLwappApMIBGroups 15 }

ciscoLwappApNotifsGroupVer1 NOTIFICATION-GROUP
   NOTIFICATIONS    {
                        ciscoLwappApIfRegulatoryDomainMismatchNotif,
                        ciscoLwappApUnsupported,
                        ciscoLwappApAssociated
                    }
    STATUS          current
    DESCRIPTION
        "This supplemental collection of objects represents the
        AP related notifications sent by the agent to a network
        management station."
    ::= { ciscoLwappApMIBGroups 16 }

ciscoLwappApGroupSup7 OBJECT-GROUP
    OBJECTS         {
                        cLApTelnetEnable,
                        cLApSshEnable,
                        cLApPreStdStateEnabled,
                        cLApPwrInjectorStateEnabled,
                        cLApPwrInjectorSelection,
                        cLApPwrInjectorSwMacAddr,
                        cLApWipsEnable,
                        cLApMonitorModeOptimization,
                        cLApDomainName,
                        cLApNameServerAddress,
                        cLApAMSDUEnable,
                        cLApEncryptionSupported,
                        cLApRogueDetectionEnabled,
                        cLApTcpMss,
                        cLApAdminStatus,
                        cLApLomEnabled,
                        cLApLegacyBeamForming,
                        cLApCdpOverAirEnabled,
                        cLApDot11IfAdminStatus,
                        cLApEthernetIfCdpEnabled,
                        cLApGlobalTcpMss,
                        cLApGlobalDot11IfCdpEnabled,
                        cLApGlobalEthernetIfCdpEnabled,
                        cLApVlanIfMode,
                        cLApVlanIfEnable,
                        cLApVlanIfNativeVlanId,
                        cLApGlobal802dot1xAuthenticationEnabled,
                        cLApGlobal802dot1xSupplicantPassword,
                        cLApGlobal802dot1xSupplicantUsername,
                        cLAp802dot1xSupplicantOverrideEnabled,
                        cLAp802dot1xSupplicantOverrideUsername,
                        cLAp802dot1xSupplicantOverridePassword,
                        cLApNwLegacyBeamForming,
                        cLApNwTxPowerThreshold,
                        cLApVlanListRowStatus,
                        cLAdjChannelRogueEnabled						
                    }
    STATUS          current
    DESCRIPTION
        "This supplemental collection of objects represents the
        information about the general attributes and functional 
        parameters of those APs that have joined the
        controller."
    ::= { ciscoLwappApMIBGroups 17 }
END
